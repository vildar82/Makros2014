Attribute VB_Name = "FormMain"
Attribute VB_Base = "0{0DEDE23D-F4B2-4075-9BE7-99F9A0703D54}{486333CE-D795-4152-9A0D-D8775D77DB03}"
Attribute VB_GlobalNameSpace = False
Attribute VB_Creatable = False
Attribute VB_PredeclaredId = True
Attribute VB_Exposed = False
Attribute VB_TemplateDerived = False
Attribute VB_Customizable = False
Option Explicit

Private Sub cmbInsert_Click()
   'вставка или создание блока доп.стержня
   
   Dim oBl As AcadBlock
   Dim oBlRef As AcadBlockReference
   Dim oActivLayer As AcadLayer
   Dim oLayerKar As AcadLayer
   Dim strCommand As String
   Dim intCmdEcho As Integer
   
   If TextBoxName = "" Then
      MsgBox "Не определено имя каркаса!", vbCritical
      Exit Sub
   End If
   
   If Not IsNumeric(TextBoxLen) Then
      MsgBox "Длина не определена!", vbCritical
      Exit Sub
   End If
   
   'текущий слой
   Set oActivLayer = ThisDrawing.ActiveLayer
   
   Set oLayerKar = ThisDrawing.Layers.Item(Functions.GetLayer("Каркасы"))
   'включаем слой без разговоров
   oLayerKar.LayerOn = True
   'если слой каркасов не текущий, то он может быть замороженным
   If Not oLayerKar Is oActivLayer Then
      oLayerKar.Freeze = False
   End If
   'делаем текущим слой каркасов
   ThisDrawing.ActiveLayer = oLayerKar
   
   'создание определения блока
   TakeBlDopSter
   
   Me.Hide
   
   intCmdEcho = ThisDrawing.GetVariable("cmdecho")
   ThisDrawing.SetVariable "cmdecho", 0
   
   'интеракртивная вставка блока
   strCommand = "(command " & _
                   Chr(34) & "._-insert" & Chr(34) & " " & _
                   Chr(34) & TextBoxName & Chr(34) & " " & _
                   "pause 1 1 pause)(princ)"
                   
   ThisDrawing.SendCommand strCommand & vbCr
   ThisDrawing.SetVariable "cmdecho", intCmdEcho
   
   'возвращаем старый текущий слой
   ThisDrawing.ActiveLayer = oActivLayer
   
End Sub

Private Sub ListBoxBl_Click()
   'определение параметров доп.стержня по его имени
   'и заполнение текстбоксов
   If ListBoxBl.ListIndex = -1 Then Exit Sub
   TextBoxName = ListBoxBl
End Sub

Private Sub TextBoxKol_AfterUpdate()
  Dim iKol As Integer
  iKol = Val(TextBoxKol)
  If iKol = 0 Then
    MsgBox "Введите число - кол-во стержней в блоке"
    TextBoxKol = 6
    Exit Sub
  End If
  TextBoxKol = iKol
   RefreshName
End Sub

Private Sub TextBoxDiam_AfterUpdate()
  If Functions.ProvDiamStandard(Val(TextBoxDiam)) = False Then
    MsgBox "Нет такого диаметра."
    TextBoxDiam = 18
    Exit Sub
  End If
   RefreshName
End Sub

Private Sub TextBoxLen_AfterUpdate()
  Dim iLenght As Integer
  iLenght = Val(TextBoxLen)
  If iLenght = 0 Then
    MsgBox "Введите число - длину"
    TextBoxLen = 2000
    Exit Sub
  End If
  TextBoxLen = iLenght
  
   RefreshName
End Sub

Private Sub TextBoxRotate_Exit(ByVal Cancel As MSForms.ReturnBoolean)
   If TextBoxRotate = "" Then Exit Sub
   If Not IsNumeric(TextBoxRotate) Then
      MsgBox "Неверный угол!", vbCritical
      TextBoxRotate = "0"
   End If
End Sub

Private Sub UserForm_Activate()
   
   'заполняем листбокс доп.стержней в этом чертеже
   
   Dim objBl As AcadBlock
   
   ListBoxBl.Clear
   For Each objBl In ThisDrawing.Blocks
      If InStr(objBl.Name, "Стержень") <> 0 Then
         ListBoxBl.AddItem objBl.Name
      End If
   Next
   
End Sub

Private Sub RefreshName()
   'определение имени доп.стержня по данным из текстбоксов
   
   If TextBoxDiam = "" Or TextBoxLen = "" Or TextBoxKol = "" Then
      Exit Sub
   End If
   
   'проверяем текстбоксы
   If Not IsNumeric(TextBoxDiam) Or Not IsNumeric(TextBoxLen) Or Not IsNumeric(TextBoxKol) Then
      MsgBox "Нужно вводить числа!", vbCritical
      Exit Sub
   End If
   
   'составляем имя для блока доп.стержня
   TextBoxName = "Стержень" & TextBoxDiam & "L" & TextBoxLen & "(шт." & TextBoxKol & ")"
   
End Sub

Private Sub TakeBlDopSter()
   'проверка наличия блока в чертеже
   'или создание определения
   Dim oBl As AcadBlock
   Dim oLine As AcadLine
   Dim bolLock As Boolean
   Dim dPt(2) As Double
   Dim dPt2(2) As Double
   
   On Error Resume Next
   
   Set oBl = ThisDrawing.Blocks.Item(CStr(TextBoxName))
   If Not oBl Is Nothing Then Exit Sub
   
   'создание блока
   Set oBl = ThisDrawing.Blocks.Add(dPt, TextBoxName)
   
   'впихиваем в него линию
   dPt2(0) = TextBoxLen: dPt2(1) = 0: dPt2(2) = 0
   Set oLine = oBl.AddLine(dPt, dPt2)
   oLine.Layer = "Каркасы"
   
End Sub

Attribute VB_Name = "Functions"
Option Explicit

Public Function GetLayer(strLayerName As String) As String
   'возвращает объект слоя, с заданным именем
   'если слоя с таким именем не было, он создается
   
   On Error GoTo HasError
   GetLayer = ThisDrawing.Layers.Item(strLayerName).Name

Exit Function

HasError:
   ThisDrawing.Layers.Add (strLayerName)
   GetLayer = strLayerName
   
End Function

Public Function ProvDiamStandard(Diam As Integer) As Boolean
   Select Case Diam
      Case 8
         ProvDiamStandard = True
      Case 10
         ProvDiamStandard = True
      Case 12
         ProvDiamStandard = True
      Case 14
         ProvDiamStandard = True
      Case 16
         ProvDiamStandard = True
      Case 18
         ProvDiamStandard = True
      Case 20
         ProvDiamStandard = True
      Case 22
         ProvDiamStandard = True
      Case 25
         ProvDiamStandard = True
      Case 28
         ProvDiamStandard = True
      Case 32
         ProvDiamStandard = True
      Case 36
         ProvDiamStandard = True
      Case 40
         ProvDiamStandard = True
      Case Else
         ProvDiamStandard = False
   End Select
   
End Function

Attribute VB_Name = "Main"
Option Explicit


Public Sub Main()
   
   FormMain.Show
   
End Sub
