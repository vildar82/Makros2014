Attribute VB_Name = "FormNodeAndObozn"
Attribute VB_Base = "0{D1C2569C-9626-4928-996B-B55AD500428D}{A6E4A065-4689-4927-9659-015F0360507F}"
Attribute VB_GlobalNameSpace = False
Attribute VB_Creatable = False
Attribute VB_PredeclaredId = True
Attribute VB_Exposed = False
Attribute VB_TemplateDerived = False
Attribute VB_Customizable = False

Option Explicit
   
   Dim colNodesAndObozn As Collection
   
Private Sub cmbExit_Click()
   hide
End Sub

Private Sub cmbGrip_Click()
   
   Dim objClNodeAndObozn As clNodeAndObozn
   Dim aobjBlNodes() As AcadBlockReference
   Dim selSetNodes As AcadSelectionSet
   Dim i As Integer
   Dim index As Integer
   
   index = ListBox1.ListIndex
   If index = -1 Then Exit Sub
   
   'определяем набор, для выносок, и передачи в лисп(для подсветки)
   Set selSetNodes = Functions.GetSelSet("Подсветка")
   
   'находим объект в коллекции узлов и обозначений
   Set objClNodeAndObozn = colNodesAndObozn.Item(ListBox1.Text & ListBox1.list(index, 1))
   
   'определяем массив блоков узлов
   ReDim aobjBlNodes(objClNodeAndObozn.colBlNodes.Count - 1)
   For i = 0 To objClNodeAndObozn.colBlNodes.Count - 1
      Set aobjBlNodes(i) = objClNodeAndObozn.colBlNodes.Item(i + 1)
   Next
   
   'заносим блоки в набор "Подсветка" и подсвечиваем
   selSetNodes.AddItems aobjBlNodes
   
   'лисповская функция для подсветки набора "Подсветка"
   ThisDrawing.SendCommand "(selset-gripset)" & vbCr
   
End Sub

Private Sub cmbSelect_Click()
   'выбор области и создание коллекции узлов и обозначений
   
   Dim objClNodeAndObozn As clNodeAndObozn
   Dim selSet As AcadSelectionSet
   Dim objBlNode As AcadBlockReference
   Dim varAtr As Variant
   Dim intCodeType(1) As Integer
   Dim varCodeDate(1) As Variant
   Dim strName As String
   Dim strObozn As String
   Dim asObozn() As String
   Dim i As Integer
   Dim j As Integer
   Dim bolYes As Boolean

   
   Set colNodesAndObozn = New Collection
   
   'запрос выбора области
   Set selSet = Functions.GetSelSet("Узлы")
   intCodeType(0) = 0: varCodeDate(0) = "insert"
   intCodeType(1) = 2: varCodeDate(1) = "Узел"
   ThisDrawing.Utility.Prompt "Выделете область для отбора блоков узлов"
   selSet.SelectOnScreen intCodeType, varCodeDate
   
   'создание коллекции блоков узлов по именам и обозначениям
   For Each objBlNode In selSet
      'определяем имя узла и обозначение
      For Each varAtr In objBlNode.GetAttributes
         If LCase(varAtr.TagString) = "марка" Then
            strName = varAtr.TextString
         ElseIf LCase(varAtr.TagString) = "обозначение" Then
            strObozn = varAtr.TextString
         End If
      Next
      'заносим блок в коллекцию узлов и обозначений
      Set objClNodeAndObozn = New clNodeAndObozn
      objClNodeAndObozn.Name = strName
      objClNodeAndObozn.Obozn = strObozn
      objClNodeAndObozn.colBlNodes.Add objBlNode
      On Error Resume Next
      Err.Clear
      colNodesAndObozn.Add objClNodeAndObozn, strName & strObozn
      If Err Then
         'если такой объект уже есть в коллекции, то добавляем только блок узла в него
         colNodesAndObozn.Item(strName & strObozn).colBlNodes.Add objBlNode
      End If
      On Error GoTo 0
   Next
   
'   'сортировка коллекции
'   Set colNodesAndObozn = Functions.SortyrColNodeAndObozn(colNodesAndObozn)
   
   ListBox1.Clear
   
   If colNodesAndObozn.Count = 0 Then
      MsgBox "Блоки узлов не найдены", vbExclamation
      Exit Sub
   End If
   
   ReDim asObozn(0)
   
   'заполняем листвиевер
   For Each objClNodeAndObozn In colNodesAndObozn
      ListBox1.AddItem objClNodeAndObozn.Name, 0
      ListBox1.list(0, 1) = objClNodeAndObozn.Obozn
      ListBox1.list(0, 2) = objClNodeAndObozn.colBlNodes.Count
      
      'составляем массив обозначений
      bolYes = False
      For i = 0 To UBound(asObozn)
         If asObozn(i) = objClNodeAndObozn.Obozn Then
            bolYes = True
         End If
      Next
      If bolYes = False Then
         ReDim Preserve asObozn(j)
         asObozn(j) = objClNodeAndObozn.Obozn
         j = j + 1
      End If
   Next
   
   'ListView1.Sorted = True
   
   'заполняем комбобокс фильтра
   ComboBoxFilter.Clear
   For i = 0 To UBound(asObozn)
      ComboBoxFilter.AddItem asObozn(i), i
   Next

End Sub
  
Private Sub ComboBoxFilter_Change()
   'вывводим список блоков узлов с заданным обозначением
   
   Dim objClNodeAndObozn As clNodeAndObozn
   
   ListBox1.Clear
   
   'заполняем листвиевер
   For Each objClNodeAndObozn In colNodesAndObozn
      If objClNodeAndObozn.Obozn = ComboBoxFilter Then
         ListBox1.AddItem objClNodeAndObozn.Name, 0
         ListBox1.list(0, 1) = objClNodeAndObozn.Obozn
         ListBox1.list(0, 2) = objClNodeAndObozn.colBlNodes.Count
      End If
   Next
   
   'ListView1.Sorted = True
   
End Sub

Private Sub UserForm_Initialize()
   
'   ListView1.ColumnHeaders.Add , , "Имя"
'   ListView1.ColumnHeaders.Add , , "Обозначение"
'   ListView1.ColumnHeaders.Add , , "Кол-во"
   
End Sub

Attribute VB_Name = "FormQuestion"
Attribute VB_Base = "0{7E3E078B-30A4-4AA7-9283-7ADA3A4981E7}{8560948D-9B25-4E3C-85E3-136EFB97A907}"
Attribute VB_GlobalNameSpace = False
Attribute VB_Creatable = False
Attribute VB_PredeclaredId = True
Attribute VB_Exposed = False
Attribute VB_TemplateDerived = False
Attribute VB_Customizable = False
Option Explicit

Private Sub cmbSelList_Click()
   LabelRes = "" 'т.е. выбор из списка
   hide
End Sub

Private Sub cmbSelSel_Click()
   LabelRes = "True" 'т.е. выбор по образце
   hide
End Sub

Private Sub UserForm_QueryClose(Cancel As Integer, CloseMode As Integer)
   LabelRes = "Выход"
   hide
End Sub

Attribute VB_Name = "FormSelNodeList"
Attribute VB_Base = "0{61FF7DE2-DE44-481D-B316-79609763F0A2}{986FA675-DC61-4DB4-B711-50E50F63192F}"
Attribute VB_GlobalNameSpace = False
Attribute VB_Creatable = False
Attribute VB_PredeclaredId = True
Attribute VB_Exposed = False
Attribute VB_TemplateDerived = False
Attribute VB_Customizable = False
Option Explicit
   
   Dim colNodeAndName As Collection
   Dim dTop As Double
   Dim dLeft As Double

Private Sub cmbExit_Click()
   hide
End Sub

Private Sub cmbRefresh_Click()
   'заполняем листбокс имен выносок
   Dim objClSpdsNode As clSpdsNodeAndName
   Dim i As Integer
   
   
   ThisDrawing.SetVariable "cmdecho", 0
   ThisDrawing.SetVariable "menuecho", 4
   ThisDrawing.SetVariable "nomutt", 1
   
   Set colNodeAndName = Functions.GetColSpdsNodeName
   
   ThisDrawing.SetVariable "cmdecho", 1
   ThisDrawing.SetVariable "menuecho", 0
   ThisDrawing.SetVariable "nomutt", 0
   
'   'сортировка коллекции
'   Set colNodeAndName = SortyrColNodes(colNodeAndName)
   
   ListBox1.Clear
   
   
   For Each objClSpdsNode In colNodeAndName
      ListBox1.AddItem objClSpdsNode.Name, 0
      'кол-во выносок с таким именем
      ListBox1.list(0, 1) = objClSpdsNode.colNodeEntity.Count
   Next
   
   'ListView1.Sorted = True

End Sub

Private Sub cmbSel_Click()
   'заносим выноски для этого номера в набор
   'в лиспе подсвечиваем набор
   
   Dim selSetNodes As AcadSelectionSet
   Dim objClNode As clSpdsNodeAndName
   Dim aobjEnt() As AcadEntity
   Dim objEnt As AcadEntity
   Dim i As Integer
   Dim index As Integer
   
   index = ListBox1.ListIndex
   If index = -1 Then Exit Sub
   
   'получаем выбранную выноску из коллекции
   Set objClNode = colNodeAndName.Item(ListBox1.Text)
   
   'переопределяем массив выносок
   ReDim aobjEnt(objClNode.colNodeEntity.Count - 1)
   
   'заносим все выноски из коллекции в массив
   For Each objEnt In objClNode.colNodeEntity
      Set aobjEnt(i) = objEnt
      i = i + 1
   Next
   
   'определяем набор, для выносок, и передачи в лисп(для подсветки)
   Set selSetNodes = Functions.GetSelSet("Подсветка")
   'заносим выноски в набор
   selSetNodes.AddItems aobjEnt
   
   'лисповская функция для подсветки набора "Подсветка"
   ThisDrawing.SendCommand "(selset-gripset)" & vbCr
   
End Sub

Private Sub UserForm_Initialize()
   
   'ListView1.ColumnHeaders.Add , , "Имя"
   'ListView1.ColumnHeaders.Add , , "Кол-во"
   
End Sub

Attribute VB_Name = "FormSelNodesSel"
Attribute VB_Base = "0{CB01CFFE-6D78-4532-BBDA-F9204864E9E0}{0003915C-808E-44E7-99F6-1547FB80D2CC}"
Attribute VB_GlobalNameSpace = False
Attribute VB_Creatable = False
Attribute VB_PredeclaredId = True
Attribute VB_Exposed = False
Attribute VB_TemplateDerived = False
Attribute VB_Customizable = False
Option Explicit

Private Sub cmbExit_Click()
   hide
End Sub

Private Sub cmbSelect_Click()
   'запускаем лисп функцию с заданными параметрами
   Dim strComand As String
   Dim bolParam As Boolean
   Dim strParam As String
   
   'формируем команду
   If CheckBoxName.value = True Then
      strParam = strParam & Chr(34) & "node" & Chr(34) & " "
   End If
   If CheckBoxLayer.value = True Then
      strParam = strParam & Chr(34) & "layer" & Chr(34) & " "
   End If
   If CheckBoxScale.value = True Then
      strParam = strParam & Chr(34) & "scale" & Chr(34) & " "
   End If
   
   If strParam = "" Then
      'если ни одна галка не стоит, то
      strComand = "(spds-node-select-like nil)" & vbCr
   Else
      strComand = "(spds-node-select-like " & "'( " & strParam & "))" & vbCr
   End If
   
   'выполняем лисповскю функцию выбора выноски по образцу выбранной от Kpblca
   ThisDrawing.SendCommand strComand
      
End Sub

Attribute VB_Name = "Functions"
Option Explicit

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function GetMacroFolder(strVBProjectName) As String
   'получение пути к корню макроса
   'без \
   Dim strMacroFolder As String
   Dim intValue As Integer
   
   On Error GoTo HasError
   
   strMacroFolder = Application.VBE.vbprojects.Item(strVBProjectName).FileName
   intValue = InStrRev(strMacroFolder, "\")
   strMacroFolder = Left(strMacroFolder, intValue - 1) 'корень с макросом, без \ на конце
   
   GetMacroFolder = strMacroFolder
   
Exit Function

HasError:
   Select Case Err.Number
      Case Else
         MsgBox "Functions, GetMacroFolder" & vbCrLf & _
               Err.Description
   End Select
   
End Function

Public Function GetColSpdsNodeName() As Collection
   'получение колекции объектов clSpdsNodeAndName, для всех выносок в текущем чертеже
   'в виде имени выноски и коллекии объектов выносок с таким именем
   
   Dim selSetNode As AcadSelectionSet
   Dim objEnt As AcadEntity
   Dim aobjEnt(0) As AcadEntity
   Dim objClassNodes As clSpdsNodeAndName
   Dim strLispFullPath As String
   Dim intCodeType() As Integer
   Dim varCodeDate() As Variant
   
   Set GetColSpdsNodeName = New Collection
   
   'создаем новый набор
   Set selSetNode = GetSelSet("Выноска")
   
   For Each objEnt In ThisDrawing.ModelSpace
      If objEnt.ObjectName = "mcsDbObjectNoteKnot" Then
         Set aobjEnt(0) = objEnt
         selSetNode.AddItems aobjEnt
         'лисп функция, записывает имя выноски из набора Выноска, в Users1
         ThisDrawing.SendCommand "(set-spdsNoteKnotName-to-Users1)" & vbCr
         Set objClassNodes = New clSpdsNodeAndName
         objClassNodes.Name = ThisDrawing.GetVariable("Users1")
         On Error Resume Next
         Err.Clear
         'добавляем новый объект в коллекцию имен выносок
         'при дублировании имени будет ошибка, и добавляем примитив к этому имени выноски в объекте objClassNodes
         GetColSpdsNodeName.Add objClassNodes, objClassNodes.Name
         If Err.Number = 0 Then
            'т.е. еще не было такого имени выноски, эта первая
            objClassNodes.colNodeEntity.Add objEnt
         Else
            'такое имя уже есть
            'добавляем примитив выноски в коллекцию выносок с таким именем
            GetColSpdsNodeName.Item(objClassNodes.Name).colNodeEntity.Add objEnt
         End If
         On Error GoTo 0
         selSetNode.Clear
      End If
   Next
   
End Function

Public Function SortyrColNodes(colObjNodes As Collection) As Collection
   'сортировка коллекции объектов clSpdsNodeAndName
   
   Dim objClNodeTemp As clSpdsNodeAndName
   Dim i As Integer
   Dim j As Integer

   For i = 1 To colObjNodes.Count - 1
      For j = 1 To colObjNodes.Count - i
         If StrComp(colObjNodes.Item(j).Name, colObjNodes.Item(j + 1).Name, vbTextCompare) = 1 Then
            Set objClNodeTemp = colObjNodes.Item(j)
            colObjNodes.Remove j
            colObjNodes.Add objClNodeTemp, objClNodeTemp.Name, , j
         End If
      Next
   Next
   
   Set SortyrColNodes = colObjNodes
      
End Function

Attribute VB_Name = "Main"
Option Explicit

'выбор узловых выносок по параметрам
'на основе лисп функции Kpblc
   
   Public Const psVBprojectName As String = "SelSpdsNode"

Public Sub Main()
   
   Dim strLispFullPath As String
   Dim strCom As String
      
   'загружаем лисп файл
   'определяем полный путь к файлу
   strLispFullPath = Functions.GetMacroFolder(psVBprojectName)
   strLispFullPath = strLispFullPath & "\SpdsNode.fas"
   strLispFullPath = Replace(strLispFullPath, "\", "/")
   'загружаем лисп файл SpdsNode.lsp из корня с макросом этого проекта
   strCom = "(load " & Chr(34) & strLispFullPath & Chr(34) & ")"
   ThisDrawing.SendCommand strCom & vbCr
   'нужно как-то проверить загрузился ли
   
   'способа выбора выносок по образцу или из списка
   FormQuestion.Show
   If FormQuestion.LabelRes = "True" Then
      'форма выбора выносок по образцу выбранной
      FormSelNodesSel.Show vbModeless
   ElseIf FormQuestion.LabelRes = "" Then
      'форма для выбора выносок из списка
      FormSelNodeList.Show vbModeless
   End If
      
End Sub

Public Sub NameAndObozn()
   'вывод списка имен узлов и их обозначений и кол-во из выбранных
   
   Dim strLispFullPath As String
   Dim strCom As String
   
   'загружаем лисп файл
   'определяем полный путь к файлу
   strLispFullPath = Functions.GetMacroFolder(psVBprojectName)
   strLispFullPath = strLispFullPath & "\SpdsNode.fas"
   strLispFullPath = Replace(strLispFullPath, "\", "/")
   'загружаем лисп файл SpdsNode.lsp из корня с макросом этого проекта
   strCom = "(load " & Chr(34) & strLispFullPath & Chr(34) & ")"
   ThisDrawing.SendCommand strCom & vbCr
   
   'вывод формы
   FormNodeAndObozn.Show vbModeless
   
End Sub

Attribute VB_Name = "VLAX"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' VLAX.CLS v1.4 (Last updated 8/27/2001)
' Copyright 1999-2001 by Frank Oquendo
'
' Permission to use, copy, modify, and distribute this software
' for any purpose and without fee is hereby granted, provided
' that the above copyright notice appears in all copies and
' that both that copyright notice and the limited warranty and
' restricted rights notice below appear in all supporting
' documentation.
'
' FRANK OQUENDO (THE AUTHOR) PROVIDES THIS PROGRAM "AS IS" AND WITH
' ALL FAULTS. THE AUTHOR SPECIFICALLY DISCLAIMS ANY IMPLIED WARRANTY
' OF MERCHANTABILITY OR FITNESS FOR A PARTICULAR USE.  THE AUTHOR
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
' VLAX.cls allows developers to evaluate AutoLISP expressions from
' Visual Basic or VBA
'
' Notes:
' All code for this class module is publicly available througout various posts
' at news://discussion.autodesk.com/autodesk.autocad.customization.vba. I do not
' claim copyright or authorship on code presented in these posts, only on this
' compilation of that code. In addition, a great big "Thank you!" to Cyrille Fauvel
' demonstrating the use of the VisualLISP ActiveX Module.
'
' Dependencies:
' Use of this class module requires the following application:
' 1. VisualLISP

Private VL As Object
Private VLF As Object

Private Sub Class_Initialize()

    Set VL = ThisDrawing.Application.GetInterfaceObject("VL.Application.1")
    Set VLF = VL.ActiveDocument.Functions

End Sub

Private Sub Class_Terminate()

    Set VLF = Nothing
    Set VL = Nothing

End Sub

Public Function EvalLispExpression(lispStatement As String)

    Dim sym As Object, RET As Object, retVal
    
    Set sym = VLF.Item("read").funcall(lispStatement)
    On Error Resume Next
    retVal = VLF.Item("eval").funcall(sym)
    If Err Then
        EvalLispExpression = ""
    Else
        EvalLispExpression = retVal
    End If

End Function

Public Sub SetLispSymbol(symbolName As String, value)

    Dim sym As Object, RET, symValue
    
    symValue = value
    Set sym = VLF.Item("read").funcall(symbolName)
    RET = VLF.Item("set").funcall(sym, symValue)
    EvalLispExpression "(defun translate-variant (data) (cond ((= (type data) 'list) (mapcar 'translate-variant data)) ((= (type data) 'variant) (translate-variant (vlax-variant-value data))) ((= (type data) 'safearray) (mapcar 'translate-variant (vlax-safearray->list data))) (t data)))"
    EvalLispExpression "(setq " & symbolName & "(translate-variant " & symbolName & "))"
    EvalLispExpression "(setq translate-variant nil)"

End Sub

Public Function GetLispSymbol(symbolName As String)

    Dim sym As Object, RET, symValue
    
    symValue = value
    Set sym = VLF.Item("read").funcall(symbolName)
    GetLispSymbol = VLF.Item("eval").funcall(sym)

End Function

Public Function GetLispList(symbolName As String) As Variant
   
   Dim sym As Object, list As Object
   Dim Count, elements(), i As Long
   
   Set sym = VLF.Item("read").funcall(symbolName)
   Set list = VLF.Item("eval").funcall(sym)
   
   Count = VLF.Item("length").funcall(list)
   
   ReDim elements(0 To Count - 1) As Variant
   
   For i = 0 To Count - 1
        elements(i) = VLF.Item("nth").funcall(i, list)
   Next
   
   GetLispList = elements
   
End Function

Public Sub NullifySymbol(ParamArray symbolName())

    Dim i As Integer
    
    For i = LBound(symbolName) To UBound(symbolName)
        EvalLispExpression "(setq " & CStr(symbolName(i)) & " nil)"
    Next

End Sub

Attribute VB_Name = "clNodeAndObozn"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
   Public colBlNodes As New Collection
   Dim strName As String
   Dim strObozn As String
   
'имя узла, т.е. отрибут марки у блока узла
Public Property Get Name() As String
   Name = strName
End Property
Public Property Let Name(ByVal vNewValue As String)
   strName = vNewValue
End Property

'обозначение узла - атрибут обозначения у блока узла
Public Property Get Obozn() As String
   Obozn = strObozn
End Property
Public Property Let Obozn(ByVal vNewValue As String)
   strObozn = vNewValue
End Property

Attribute VB_Name = "clSpdsNodeAndName"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
   Public colNodeEntity As New Collection
'   Dim fobjNode As AcadEntity
   Dim strName As String
   
''блок выноски
'Public Property Get objNode() As AcadEntity
'   Set objNode = fobjNode
'End Property
'Public Property Let objNode(ByVal vNewValue As AcadEntity)
'   Set fobjNode = vNewValue
'End Property

'имя выноски (т.е. имя узла - первая строка в выноске)
Public Property Get Name() As String
   Name = strName
End Property
Public Property Let Name(ByVal vNewValue As String)
   strName = vNewValue
End Property
