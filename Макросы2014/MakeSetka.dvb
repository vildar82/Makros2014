Attribute VB_Name = "FormInsSetka"
Attribute VB_Base = "0{88E07410-3E7C-4FE8-A0F7-FE56CA9AB933}{09435415-0E90-46E5-9C20-07437E2CAE2C}"
Attribute VB_GlobalNameSpace = False
Attribute VB_Creatable = False
Attribute VB_PredeclaredId = True
Attribute VB_Exposed = False
Attribute VB_TemplateDerived = False
Attribute VB_Customizable = False
Option Explicit

Private Sub CheckBoxQuadro_Click()
   
   TextBoxWidth.Enabled = Not CheckBoxQuadro.Value
   
End Sub

Private Sub cmbExit_Click()
   hide
End Sub

Private Sub cmbInsert_Click()
   
   'вставка блока сетки
   If TextBoxMarkaSetky = "" Then
      MsgBox "Имя для блока сетки не определено!", vbCritical
      Exit Sub
   End If
   
   Me.hide
   
   Dim sBlName As String
   Dim sValue As String
   Dim oLayer As AcadLayer
   
   'размораживаем 0 слой
   Set oLayer = ThisDrawing.Layers.Item(Functions.GetLayer("0"))
   If Not ThisDrawing.ActiveLayer Is oLayer Then
      oLayer.Freeze = False
   End If
   oLayer.LayerOn = True
   oLayer.Lock = False

   'размораживаем слой марки
   Set oLayer = ThisDrawing.Layers.Item(Functions.GetLayer("Att~Marka"))
   If Not ThisDrawing.ActiveLayer Is oLayer Then
      oLayer.Freeze = False
   End If
   oLayer.LayerOn = True
   oLayer.Lock = False
   
   'вставлять будем на слой Каркасы
   Set oLayer = ThisDrawing.Layers.Item(Functions.GetLayer("Каркасы"))
   If Not ThisDrawing.ActiveLayer Is oLayer Then
      oLayer.Freeze = False
   End If
   oLayer.LayerOn = True
   oLayer.Lock = False
   ThisDrawing.ActiveLayer = oLayer
   
   On Error Resume Next
   sValue = TextBoxSetkaBlName
   sBlName = ThisDrawing.Blocks.Item(sValue).Name
   If sBlName = "" Then
      'создаем блок сетки
      MakeBlockSetky TextBoxSetkaBlName, TextBoxMarkaSetky, CInt(TextBoxKolSetok)
      sBlName = TextBoxSetkaBlName
   End If
   
   'вставляем блок сетки
   Dim intAttreq As Integer
   Dim intCmdEcho As Integer
   Dim strCommand As String
   
   intAttreq = ThisDrawing.GetVariable("attreq")
   ThisDrawing.SetVariable "attreq", 0
   intCmdEcho = ThisDrawing.GetVariable("cmdecho")
   ThisDrawing.SetVariable "cmdecho", 0
   strCommand = "(command " & _
                   Chr(34) & "._-insert" & Chr(34) & " " & _
                   Chr(34) & sBlName & Chr(34) & _
                   " pause 1 1 0)(princ)"
   ThisDrawing.SendCommand strCommand & vbCr
   ThisDrawing.SetVariable "attreq", intAttreq
   ThisDrawing.SetVariable "cmdecho", intCmdEcho
   
End Sub

Private Sub ListBoxSetkiInCurDraw_Click()
   
   Dim sBlName As String
   Dim sMarkaSetky As String
   Dim intKol As Integer
   Dim intVal As Integer
   
   If ListBoxSetkiInCurDraw.ListIndex = -1 Then
      Exit Sub
   End If
   
   sBlName = ListBoxSetkiInCurDraw
   
   'определяем марку
   intVal = InStr(LCase(sBlName), "(шт.")
   If intVal = 0 Then
      sMarkaSetky = Mid(sBlName, 7)
      intKol = 1
   Else
      sMarkaSetky = Mid(sBlName, 7, intVal - 7)
      intKol = Val(Mid(sBlName, intVal + 4))
   End If
   
   TextBoxMarkaSetky = sMarkaSetky
   TextBoxKolSetok = intKol
   
End Sub

Private Sub TextBoxKolSetok_Change()
   
   If IsNumeric(TextBoxKolSetok) = False Then
      MsgBox "Нужно ввести число", vbCritical
      TextBoxKolSetok = 1
   Else
      'приводим к целому числу
      If CInt(TextBoxKolSetok) < 0 Then
         TextBoxKolSetok = 1
      Else
         TextBoxKolSetok = CInt(TextBoxKolSetok)
      End If
   End If
   
   'изменяем имя блока в TextBoxSetkaBlName
   ChangeSetkaBlName
   
End Sub

Private Sub TextBoxMarkaSetky_Change()
   
   If TextBoxMarkaSetky <> "" Then
      'изменяем имя блока в TextBoxSetkaBlName
      ChangeSetkaBlName
   End If
   
End Sub

Private Sub UserForm_Activate()
   
   Dim oBl As AcadBlock
   
   'определяем блоки сеток определенные в текущем чертеже
   'и добавляем их в листбокс
   ListBoxSetkiInCurDraw.Clear
   For Each oBl In ThisDrawing.Blocks
      If oBl.Name Like ("Сетка *") Then
         ListBoxSetkiInCurDraw.AddItem oBl.Name
      End If
   Next
   
   'изменяем имя блока в TextBoxSetkaBlName
   ChangeSetkaBlName
   
End Sub

Private Sub ChangeSetkaBlName()
   'определяем имя блока сетки
   
   If TextBoxKolSetok <> "" And TextBoxMarkaSetky <> "" Then
      If CInt(TextBoxKolSetok) = 1 Then
         TextBoxSetkaBlName = "Сетка " & TextBoxMarkaSetky
      Else
         TextBoxSetkaBlName = "Сетка " & TextBoxMarkaSetky & "(шт." & CInt(TextBoxKolSetok) & ")"
      End If
   Else
      TextBoxSetkaBlName = ""
   End If
   
End Sub

Private Sub MakeBlockSetky(sBlName As String, sMarka As String, intKol As Integer)
   
   'создаем блок сетки
   Dim oBl As AcadBlock
   Dim dInsPt(2) As Double
   Dim strAttrFullPath As String
   Dim objBlRef As AcadBlockReference
   Dim oAttrMarka As AcadAttribute
   Dim oAttr As AcadAttribute
   Dim varExpl As Variant
   Dim dPt(2) As Double
   Dim dPtMarka(2) As Double
   Dim dPtShtuk(2) As Double
   Dim intLenght As Integer
   Dim intWidth As Integer
   Dim dPtRec1(2) As Double
   Dim dPtRec2(2) As Double
   Dim dPtRec3(2) As Double
   Dim dPtRec4(2) As Double
   Dim points(0 To 11) As Double
   Dim oPolyLine As AcadPolyline
   Dim oLine As AcadLine
   
   Set oBl = ThisDrawing.Blocks.Add(dInsPt, sBlName)
   
   'Functions.GetLayer "Att~Marka"
   
   intLenght = TextBoxLenght
   If CheckBoxQuadro.Value = True Then
      intWidth = intLenght
   Else
      intWidth = TextBoxWidth
   End If
   
   If intKol = 1 Then
      dPtMarka(1) = intWidth / 2 + 50
   Else
      dPtMarka(1) = intWidth / 2 + 350
      dPtShtuk(1) = intWidth / 2 + 50
   End If
   
   'вставляем атрибут марки
   'вставляем блок атрибута из \\Sgpsrv2\СПД\Конструкторы\Макросы\SpecRost\Attr.dwg
   strAttrFullPath = Functions.GetMacroFolder(psVBProjectName) & "\Блоки\Attr.dwg"
   Set objBlRef = oBl.InsertBlock(dPt, strAttrFullPath, 1, 1, 1, 0)
   varExpl = objBlRef.Explode
   objBlRef.Delete
   Set oAttrMarka = varExpl(0)
   oAttrMarka.TextAlignmentPoint = dPtMarka
   oAttrMarka.TagString = "Марка"
   oAttrMarka.TextString = sMarka
   oAttrMarka.PromptString = "Марка сетки"
   
   If intKol <> 1 Then
      'создаем атрибут кол-во
      Set oAttr = oAttrMarka.Copy
      oAttr.TextAlignmentPoint = dPtShtuk
      oAttr.Layer = "Каркасы"
      oAttr.TagString = "Кол-во"
      oAttr.TextString = "шт." & intKol
      oAttr.PromptString = "Кол-во сеток"
   End If
   
   'рисуем прямоугольник
   dPtRec1(0) = -(intLenght / 2): dPtRec1(1) = -(intWidth / 2)
   dPtRec2(0) = dPtRec1(0): dPtRec2(1) = dPtRec1(1) + intWidth
   dPtRec3(0) = dPtRec2(0) + intLenght: dPtRec3(1) = dPtRec2(1)
   dPtRec4(0) = dPtRec3(0): dPtRec4(1) = dPtRec1(1)
   
   points(0) = -(intLenght / 2): points(1) = -(intWidth / 2): points(2) = 0
   points(3) = points(0): points(4) = points(1) + intWidth: points(5) = 0
   points(6) = points(3) + intLenght: points(7) = points(4): points(8) = 0
   points(9) = points(6): points(10) = points(1): points(11) = 0
   
   Set oPolyLine = oBl.AddPolyline(points)
   oPolyLine.Layer = "0"
   oPolyLine.Linetype = "ByBlock"
   oPolyLine.Lineweight = acLnWtByBlock
   oPolyLine.color = acByBlock
   oPolyLine.Closed = True
   oPolyLine.LinetypeScale = 50
   
   Set oLine = oBl.AddLine(dPtRec1, dPtRec3)
   oLine.Layer = "0"
   oLine.Linetype = "ByBlock"
   oLine.Lineweight = acLnWtByBlock
   oLine.color = acByBlock
   oLine.LinetypeScale = 50
   Set oLine = oBl.AddLine(dPtRec2, dPtRec4)
   oLine.Layer = "0"
   oLine.Linetype = "ByBlock"
   oLine.Lineweight = acLnWtByBlock
   oLine.color = acByBlock
   oLine.LinetypeScale = 50
   
End Sub

Attribute VB_Name = "Functions"
Option Explicit

Public Function GetMacroFolder(strVBProjectName) As String
   'получение пути к корню макроса
   'без \
   Dim strMacroFolder As String
   Dim intValue As Integer
   
   On Error GoTo HasError
   
   strMacroFolder = Application.VBE.vbprojects.Item(psVBProjectName).FileName
   intValue = InStrRev(strMacroFolder, "\")
   strMacroFolder = Left(strMacroFolder, intValue - 1) 'корень с макросом, без \ на конце
   
   GetMacroFolder = strMacroFolder
   
Exit Function
HasError:
   MsgBox "Functions, GetMacroFolder" & vbCrLf & _
               Err.Description
End Function

Public Function GetLayer(strLayerName As String) As String
   'возвращает объект слоя, с заданным именем
   'если слоя с таким именем не было, он создается
   
   On Error GoTo HasError
   GetLayer = ThisDrawing.Layers.Item(strLayerName).Name

Exit Function

HasError:
   ThisDrawing.Layers.Add (strLayerName)
   GetLayer = strLayerName
   
End Function

Attribute VB_Name = "Main"
Option Explicit
'Создание блока сетки для расчета спецификаций ростверка

Public Const psVBProjectName As String = "SpecRost_MakeBlSetka"

Public Sub Main()
   
   FormInsSetka.Show
   
End Sub
