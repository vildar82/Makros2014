Attribute VB_Name = "FormMain"
Attribute VB_Base = "0{7EFCDE1F-CA52-4474-8548-C6F19AD1EA1B}{4DB8F726-67A5-4466-AEF7-96AE9CF746CE}"
Attribute VB_GlobalNameSpace = False
Attribute VB_Creatable = False
Attribute VB_PredeclaredId = True
Attribute VB_Exposed = False
Attribute VB_TemplateDerived = False
Attribute VB_Customizable = False
Option Explicit

  Const pi As Double = 3.14159265358979

Private Sub cmbExit_Click()
  hide
End Sub

Private Sub cmbRotate_Click()
  
  Dim selSet As AcadSelectionSet
  Dim oBlRef As AcadBlockReference
  Dim oEnt As AcadEntity
  Dim intCode(1) As Integer
  Dim vDate(1) As Variant
  Dim varAtr As Variant
  Dim oAtrRef As AcadAttributeReference
  Dim dDopusk As Double
  Dim dAngleOld As Double
  Dim dAngleNew As Double
  Dim dAngleAtr As Double 'значение поворота атрибута в градусах
  Dim oLayer As AcadLayer
  
  Me.hide
  
  Set oLayer = GetLayer("Att~Marka")
  If Not oLayer Is Nothing Then
    oLayer.Lock = False
  End If
  
  
  dDopusk = Val(TextBoxDopusk)
  dAngleOld = Val(TextBoxAngleOld)
  dAngleNew = GetAtrAngleRad(Val(TextBoxAngleNew))
  
  Set selSet = Functions.GetSelSet("Блоки с атрибутами")
  
  intCode(0) = 0: vDate(0) = "insert"
  intCode(1) = 66: vDate(1) = 1
  
  ThisDrawing.Utility.Prompt vbCrLf & "Выбор блоков с атрибутами"
  selSet.SelectOnScreen intCode, vDate
  
  For Each oEnt In selSet
    If TypeOf oEnt Is AcadBlockReference Then
'      Set oBlRef = oEnt
      For Each varAtr In oEnt.GetAttributes
'        Set oAtrRef = varAtr
        If varAtr.Layer = "Att~Marka" Then
          dAngleAtr = GetAtrAngleGrad(varAtr.Rotation)
          If dAngleAtr >= (dAngleOld - dDopusk) And dAngleAtr <= (dAngleOld + dDopusk) Then
            varAtr.Rotation = dAngleNew
            Exit For
          End If
        End If
      Next
    End If
  Next
  
End Sub


Private Sub TextBoxAngleNew_Exit(ByVal Cancel As MSForms.ReturnBoolean)
  TextBoxAngleNew = Val(TextBoxAngleNew)
End Sub


Private Sub TextBoxAngleOld_Exit(ByVal Cancel As MSForms.ReturnBoolean)
  TextBoxAngleOld = Val(TextBoxAngleOld)
End Sub

Private Sub TextBoxDopusk_Exit(ByVal Cancel As MSForms.ReturnBoolean)
  TextBoxDopusk = Val(TextBoxDopusk)
End Sub

Private Function GetAtrAngleGrad(dAngleRad As Double) As Double
  GetAtrAngleGrad = dAngleRad * 180 / pi
End Function
Private Function GetAtrAngleRad(dAngleGrad As Double) As Double
  GetAtrAngleRad = dAngleGrad * pi / 180
End Function

Attribute VB_Name = "Functions"
Option Explicit

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Attribute VB_Name = "Main"
Option Explicit

'поворот атрибутов блоков

Public Sub Main()
  FormMain.Show
End Sub

Public Function GetLayer(strLayerName As String) As AcadLayer
   'возвращает объект слоя, с заданным именем
   'если слоя с таким именем не было, он создается
   
   On Error GoTo HasError
   Set GetLayer = ThisDrawing.Layers.Item(strLayerName)

Exit Function

HasError:
'   ThisDrawing.Layers.Add (strLayerName)
'   GetLayer = strLayerName
   
End Function
