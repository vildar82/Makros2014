Attribute VB_Name = "FormDetailEdit"
Attribute VB_Base = "0{A310FBDA-7B40-48A1-AABB-2C6DF24C52D3}{39FFB9B3-EE0B-40EB-B395-2E3C5AB118A1}"
Attribute VB_GlobalNameSpace = False
Attribute VB_Creatable = False
Attribute VB_PredeclaredId = True
Attribute VB_Exposed = False
Attribute VB_TemplateDerived = False
Attribute VB_Customizable = False
Option Explicit

Private Sub cmbExit_Click()
   bolYes = False
   Hide
End Sub

Private Sub cmbOK_Click()
   'масса не должна быть пустой
   If IsNumeric(TextBoxMassa) = False Then
      TextBoxMassa = Funcions.ReplaceDelimiter(TextBoxMassa)
'      MsgBox "Не правильно введена масса!", vbCritical
'      Exit Sub
   End If
   If ComboBoxSer.Visible = True Then
      If ComboBoxSer.ListIndex = -1 Then
         MsgBox "Нужно выбрать серию!", vbCritical, pcsVBProjectName
         Exit Sub
      End If
   End If
   If ComboBoxObozn.Visible = True Then
      If ComboBoxObozn.ListIndex = -1 Then
         MsgBox "Нужно выбрать обозначение!", vbCritical, pcsVBProjectName
         Exit Sub
      End If
   End If
   
   'преобразовываем имя детали, рускую х заменяем английским x
   TextBoxName = Replace(TextBoxName, "х", "x")
   
   bolYes = True
   Hide
End Sub

Private Sub ComboBoxSer_Change()
   'т.е. это деталь наша, выводим список альбомов для выбранной серии из таьбл альбомов
   
   Dim objRec As New ADODB.Recordset
   Dim strSql As String
   Dim index As Integer
   
   On Error GoTo HasError
   
   index = ComboBoxSer.ListIndex
   If index = -1 Then
'      MsgBox "Нужно выбрать серию!"
      Exit Sub
   End If
   
   'запрос Obozn по выбранной серии из таблицы Альбомы
   strSql = "SELECT * FROM Альбомы INNER JOIN Серии ON Альбомы.Ser_ID = Серии.ID WHERE Серии.Ser = '" & ComboBoxSer & "' ORDER BY Obozn;"
   'создаем рекордсет
   objRec.Open Source:=strSql, ActiveConnection:=objConect, _
            CursorType:=adOpenKeyset, LockType:=adLockOptimistic, Options:=adCmdText
   If objRec.EOF And objRec.BOF Then
      MsgBox "Создайте серию в форме каталога узлов!", vbCritical, pcsVBProjectName
      Exit Sub
   End If
   
   ComboBoxObozn.Clear
   
   objRec.MoveFirst
   Do Until objRec.EOF
      ComboBoxObozn.AddItem objRec!Obozn
      objRec.MoveNext
   Loop
   
Exit Sub
HasError:
   MsgBox Err.Description, vbCritical, pcsVBProjectName
   
End Sub

Private Sub TextBoxMassa_Exit(ByVal Cancel As MSForms.ReturnBoolean)
   'проверить число, заменить запятую или точку на разделитель
   On Error GoTo HasError
   Dim changeDelim As String
   Dim resMassa As Double
   changeDelim = Funcions.ReplaceDelimiter(TextBoxMassa)
   resMassa = CDbl(changeDelim)
   TextBoxMassa = resMassa
Exit Sub
HasError:
   Dim sErr As String
   sErr = "Проверьте, возможно вы ввели не число! " & vbCrLf & Err.Description
   MsgBox sErr, vbCritical, pcsVBProjectName
End Sub

Attribute VB_Name = "FormDetails"
Attribute VB_Base = "0{A11D0FF0-3454-44DA-BA3D-29407675E834}{C4C0D8E5-496A-4D1E-8E8F-4ADEB84F9D59}"
Attribute VB_GlobalNameSpace = False
Attribute VB_Creatable = False
Attribute VB_PredeclaredId = True
Attribute VB_Exposed = False
Attribute VB_TemplateDerived = False
Attribute VB_Customizable = False
Option Explicit
   
   Dim recSet As New ADODB.Recordset
   Dim recTablDet As New ADODB.Recordset
   Dim strCurSer As String 'текущий выбранная серия в редакторе базы узлов
   Dim bolEditOrAdd As Boolean

Private Sub cmbDetailAdd_Click()
   'добавление новой детали в таблицу
   
   Dim recSetTemp As New ADODB.Recordset
   Dim strSql As String
   Dim strTablName As String
   Dim i As Integer
   
   On Error GoTo HasError
   
   If ComboBoxTables.ListIndex = -1 Then
      MsgBox "Нужно выбрать каталог изделий!", vbCritical, pcsVBProjectName
      Exit Sub
   End If
   
   FormDetailEdit.Caption = "Добавление нового изделия в каталог " & ComboBoxTables
   'настраиваем форму для заполнения данных по детале
   Select Case ComboBoxTables
      Case "Наши изделия"
         FormDetailEdit.LabelObozn.Visible = True
         FormDetailEdit.TextBoxObozn.Visible = True
         FormDetailEdit.LabelName = "МС1"
         FormDetailEdit.TextBoxName = "МС1"
         FormDetailEdit.LabelObozn.Visible = False
         FormDetailEdit.TextBoxObozn.Visible = False
         FormDetailEdit.LabelNaimen = "Изделие соединительное"
         FormDetailEdit.TextBoxNaimen = "Изделие соединительное"
         'запрос альбомов для серии из таблицы альбомов
         'создаем рекордсет
         'выбор серии для детали
         FormDetailEdit.ComboBoxObozn.Visible = True
         FormDetailEdit.ComboBoxSer.Visible = True
         FormDetailEdit.LabelSer.Visible = True
         FormDetailEdit.LabelSer = "Серия:"
         FormDetailEdit.ComboBoxSer.Clear
         'заполняем комбобокс серий
         FormDetailEdit.ComboBoxSer.Clear
         For i = 0 To FormNodes.ComboBoxSer.ListCount - 1
            If FormNodes.ComboBoxSer.List(i, 0) <> "Типовые" Then
               FormDetailEdit.ComboBoxSer.AddItem FormNodes.ComboBoxSer.List(i, 0)
            End If
         Next
         'если есть фильтр по серии и по альбому, то выбираем их в комбобоксах
         If ComboBoxFilterSer <> "" And ComboBoxFilterSer <> "Все" Then
            FormDetailEdit.ComboBoxSer.Text = ComboBoxFilterSer
            'выбираем альбом
            If ComboBoxFilterAlbom <> "" And ComboBoxFilterAlbom <> "Все" Then
               FormDetailEdit.ComboBoxObozn = ComboBoxFilterAlbom
            End If
         End If
      Case "Уголки"
         FormDetailEdit.LabelObozn.Visible = True
         FormDetailEdit.TextBoxObozn.Visible = True
         FormDetailEdit.ComboBoxObozn.Visible = False
         FormDetailEdit.LabelName = "по английски!!!"
         FormDetailEdit.TextBoxName = "125x9 L=100"
         FormDetailEdit.LabelObozn = ""
         FormDetailEdit.TextBoxObozn = ""
         FormDetailEdit.LabelNaimen = "Уголок"
         FormDetailEdit.TextBoxNaimen = "Уголок"
         FormDetailEdit.ComboBoxSer.Visible = False
         FormDetailEdit.LabelSer.Visible = False
      Case "Стержни"
         FormDetailEdit.ComboBoxObozn.Visible = False
         FormDetailEdit.LabelObozn.Visible = True
         FormDetailEdit.TextBoxObozn.Visible = True
         FormDetailEdit.LabelName = "12-AI L=500"
         If ListBoxTableDetails.ListIndex >= 0 Then 'Not ListViewTablDetails.SelectedItem Is Nothing Then
            FormDetailEdit.TextBoxName = ListBoxTableDetails.Text    'ListViewTablDetails.SelectedItem.Text
         Else
            FormDetailEdit.TextBoxName = "12-AI L=500"
         End If
         FormDetailEdit.TextBoxObozn = ""
         FormDetailEdit.LabelObozn = ""
         FormDetailEdit.LabelNaimen = "Стержень"
         FormDetailEdit.TextBoxNaimen = "Стержень"
         FormDetailEdit.ComboBoxSer.Visible = False
         FormDetailEdit.LabelSer.Visible = False
      Case "Пластины"
         FormDetailEdit.ComboBoxObozn.Visible = False
         FormDetailEdit.LabelObozn.Visible = True
         FormDetailEdit.TextBoxObozn.Visible = True
         FormDetailEdit.LabelName = "x - английский!!!"
         'если что-то выбрано
         If ListBoxTableDetails.ListIndex >= 0 Then 'Not ListViewTablDetails.SelectedItem Is Nothing Then
            FormDetailEdit.TextBoxName = ListBoxTableDetails.Text
         Else
            FormDetailEdit.TextBoxName = "8x30x150"
         End If
         FormDetailEdit.LabelObozn = ""
         FormDetailEdit.TextBoxObozn = ""
         FormDetailEdit.LabelNaimen = "Пластина"
         FormDetailEdit.TextBoxNaimen = "Пластина"
         FormDetailEdit.ComboBoxSer.Visible = False
         FormDetailEdit.LabelSer.Visible = False
      Case "Типовые"
         FormDetailEdit.LabelName = "ИМ1"
         FormDetailEdit.TextBoxName = "ИМ1"
         FormDetailEdit.LabelObozn.Visible = False
         FormDetailEdit.TextBoxObozn.Visible = False
         FormDetailEdit.LabelNaimen = "Изделие соединительное"
         FormDetailEdit.TextBoxNaimen = "Изделие соединительное"
         FormDetailEdit.ComboBoxSer.Visible = False
         FormDetailEdit.LabelSer.Visible = False
         FormDetailEdit.ComboBoxObozn.Visible = True
         'запрос альбомов по типовым сериячм из Альбомов
         strSql = "SELECT Obozn FROM Альбомы INNER JOIN Серии ON Альбомы.Ser_ID = Серии.ID WHERE Серии.Ser = 'Типовые' ORDER BY Ser"
         recSetTemp.Open Source:=strSql, ActiveConnection:=objConect, _
            CursorType:=adOpenKeyset, LockType:=adLockOptimistic, Options:=adCmdText
         If recSetTemp.EOF And recSetTemp.BOF Then
            'нет альбомов в типовой серии
            MsgBox "Нужно создать альбом для типовой серии в форме каталога узлов!", vbCritical, pcsVBProjectName
            Exit Sub
         End If
         FormDetailEdit.ComboBoxObozn.Clear
         recSetTemp.MoveFirst
         Do Until recSetTemp.EOF
            FormDetailEdit.ComboBoxObozn.AddItem recSetTemp!Obozn
            recSetTemp.MoveNext
         Loop
         
   End Select
   
   bolYes = False
   FormDetailEdit.Show
   If bolYes = False Then
      'нажали отмену
      Exit Sub
   End If
   
   
   'добавляем новую запись
   recTablDet.AddNew
   'ужна обработка ошибке при дублировании имени
   recTablDet!Name = FormDetailEdit.TextBoxName
   recTablDet!Massa = CDbl(FormDetailEdit.TextBoxMassa)
   recTablDet!Naimen = FormDetailEdit.TextBoxNaimen
   If ComboBoxTables = "Наши изделия" Then
      'нужно узнать какая серия выбрана для детали
      recTablDet!Obozn = FormDetailEdit.ComboBoxObozn
      recTablDet!Type = FormDetailEdit.ComboBoxSer
   ElseIf ComboBoxTables = "Типовые" Then
      recTablDet!Obozn = FormDetailEdit.ComboBoxObozn
      recTablDet!Type = ComboBoxTables
   Else
      recTablDet!Type = ComboBoxTables
      recTablDet!Obozn = FormDetailEdit.TextBoxObozn
   End If
   recTablDet!Примечание = FormDetailEdit.TextBoxPrimech
   recTablDet.Update
   'возможна ошибка при дублировании имени изделия
   'в таком случае выдаем сообщение и возвращаем в форму FormDetailEdit для исправления
   'по хорошему надо роазать где уже есть эта деталь и в каких узлах она используется
   
   'если все ок, добавляем запись в листвиевер
   'Set objListItem = ListViewTablDetails.ListItems.Add(, , recTablDet!Name)
   ListBoxTableDetails.AddItem recTablDet!Name, 0
   ListBoxTableDetails.List(0, 1) = recTablDet!Obozn
   ListBoxTableDetails.List(0, 2) = recTablDet!Massa
   ListBoxTableDetails.List(0, 3) = recTablDet!Naimen
   ListBoxTableDetails.List(0, 4) = recTablDet!Type
   ListBoxTableDetails.List(0, 5) = recTablDet!ID
   ListBoxTableDetails.List(0, 6) = recTablDet!Примечание
   ListBoxTableDetails.Selected(0) = True
   'objListItem.Selected = True
   
Exit Sub

HasError:
   Select Case Err.Number
      Case -2147217887
         'дублирование записей
         'точно:"Изменения не были успешно внесены из-за повторяющихся значений в индексе, ключевых полях или связях.  Измените данные в поле или полях, содержащих повторяющиеся значения, удалите индекс или переопределите его, чтобы разрешить повторяющиеся значения, и п"
         MsgBox "Такая деталь уже есть", vbCritical, pcsVBProjectName
'         recTablDet.Requery
      Case Else
         MsgBox "FormDetails, cmbDetailAdd_Click" & vbCrLf & _
               Err.Description, vbCritical, pcsVBProjectName
'         recTablDet.Requery
   End Select
   
End Sub

Private Sub cmbDetailDel_Click()
   'удаление записи об изделии из таблицы и из всех узлов
   
   Dim lID As Long
   Dim index As Integer
   
   On Error GoTo HasError
   
   'Set objListItem = ListViewTablDetails.SelectedItem
   index = ListBoxTableDetails.ListIndex
   
   If index = -1 Then
      'не выбрано изделие для удаления из базы
      MsgBox "Не выбрано изделие для его удаления!", vbCritical, pcsVBProjectName
      Exit Sub
   End If
   
   'подтверждение удаления
   If MsgBox("Удалить изделие - " & ListBoxTableDetails.Text, vbQuestion + vbYesNo, pcsVBProjectName) = vbNo Then
      Exit Sub
   End If
   
   lID = ListBoxTableDetails.List(index, 5)    'objListItem.ListSubItems(5)
   
   'удаляем из базы
   'запрос детали в рекордсет из таблицы Изделий
   recTablDet.MoveFirst
   If recTablDet!ID <> lID Then
      recTablDet.Find "ID = '" & lID & "'"
   End If
   recTablDet.Delete
   recTablDet.Update
   
   'удаляем из листвиевера
   'ListViewTablDetails.ListItems.Remove index
   ListBoxTableDetails.RemoveItem index
   
Exit Sub

HasError:
   Select Case Err.Number
      Case Else
         MsgBox Err.Description, vbCritical, pcsVBProjectName
   End Select
   
End Sub

Private Sub cmbDetailEdit_Click()
   'редактирвание детали
   
   Dim recSetTemp As New ADODB.Recordset
   Dim lID As Long
   Dim index As Integer
   Dim i As Integer
   Dim strSql As String
   
   On Error GoTo HasError
   
   'если не выбран тип в комбобоксе
   If ComboBoxTables.ListIndex = -1 Then
      'не выбрано тип изделий
      MsgBox "Не выбран каталог изделий!", vbCritical, pcsVBProjectName
      Exit Sub
   End If
   'выделенный элемент в листвиевере
   'Set objListItem = ListViewTablDetails.SelectedItem
   index = ListBoxTableDetails.ListIndex
   'если не выбрано ниче
   If index = -1 Then
      'не выбрано изделие для редактирования из базы
      MsgBox "Не выбрано изделие для его редактирования!", vbExclamation, pcsVBProjectName
      Exit Sub
   End If
   
   'уникальное номер редактируемой детали
   lID = ListBoxTableDetails.List(index, 5)  'objListItem.ListSubItems.Item(5)
   
   'находим деталь в RecSet
   recTablDet.MoveFirst
   If recTablDet!ID <> lID Then
      recTablDet.Find "ID = '" & lID & "'"
   End If
   
   'подготовка формы для редактирования
   FormDetailEdit.Caption = "Редактирование изделия в каталоге " & ComboBoxTables
   'настраиваем форму для заполнения данных по детале
   FormDetailEdit.LabelName = ListBoxTableDetails.Text '  objListItem.Text
   FormDetailEdit.TextBoxName = ListBoxTableDetails.Text 'objListItem.Text
   FormDetailEdit.TextBoxMassa = ListBoxTableDetails.List(index, 2)  'objListItem.ListSubItems(2).Text
   FormDetailEdit.LabelMassa = ListBoxTableDetails.List(index, 2) 'objListItem.ListSubItems(2).Text
   FormDetailEdit.LabelNaimen = ListBoxTableDetails.List(index, 3) 'objListItem.ListSubItems(3).Text
   FormDetailEdit.TextBoxNaimen = ListBoxTableDetails.List(index, 3) 'objListItem.ListSubItems(3).Text
   FormDetailEdit.TextBoxPrimech = ListBoxTableDetails.List(index, 6) 'objListItem.ListSubItems(6).Text
   If ComboBoxTables = "Наши изделия" Then
      FormDetailEdit.ComboBoxObozn.Visible = True
      FormDetailEdit.ComboBoxSer.Visible = True
      FormDetailEdit.TextBoxObozn.Visible = False
      'заполняем серии
      FormDetailEdit.ComboBoxSer.Clear
      'запрос серий
      If recSet.State = adStateOpen Then recSet.Close
      strSql = "SELECT Ser FROM Серии;"
      recSet.Open Source:=strSql, ActiveConnection:=objConect, _
         CursorType:=adOpenStatic, LockType:=adLockReadOnly, Options:=adCmdText
      If recSet.EOF And recSet.BOF Then Exit Sub
      recSet.MoveFirst
      Do While Not recSet.EOF
         FormDetailEdit.ComboBoxSer.AddItem recSet!Ser
         recSet.MoveNext
      Loop
      FormDetailEdit.ComboBoxSer = ListBoxTableDetails.List(index, 4) 'objListItem.ListSubItems(4).Text 'Type
      FormDetailEdit.ComboBoxObozn = ListBoxTableDetails.List(index, 1) 'objListItem.ListSubItems(1).Text
      
   ElseIf ComboBoxTables = "Типовые" Then
      FormDetailEdit.ComboBoxObozn.Visible = True
      FormDetailEdit.ComboBoxSer.Visible = False
      FormDetailEdit.TextBoxObozn.Visible = False
      'запрос альбомов по типовым сериячм из Альбомов
         strSql = "SELECT Obozn FROM Альбомы INNER JOIN Серии ON Альбомы.Ser_ID = Серии.ID WHERE Серии.Ser = 'Типовые' ORDER BY Ser"
         recSetTemp.Open Source:=strSql, ActiveConnection:=objConect, _
            CursorType:=adOpenKeyset, LockType:=adLockOptimistic, Options:=adCmdText
         If recSetTemp.EOF And recSetTemp.BOF Then
            'нет альбомов в типовой серии
            MsgBox "Нужно создать альбом для типовой серии в форме каталога узлов!", vbCritical, pcsVBProjectName
            Exit Sub
         End If
         FormDetailEdit.ComboBoxObozn.Clear
         recSetTemp.MoveFirst
         Do Until recSetTemp.EOF
            FormDetailEdit.ComboBoxObozn.AddItem recSetTemp!Obozn
            recSetTemp.MoveNext
         Loop
         FormDetailEdit.ComboBoxObozn = ListBoxTableDetails.List(index, 1)
   Else
      FormDetailEdit.ComboBoxObozn.Visible = False
      FormDetailEdit.ComboBoxSer.Visible = False
      FormDetailEdit.TextBoxObozn.Visible = True
      FormDetailEdit.TextBoxObozn = ListBoxTableDetails.List(index, 1)
      FormDetailEdit.LabelObozn = ListBoxTableDetails.List(index, 1)
   End If
   
   'устанавливаем текущую серию редактируемой детали
   recTablDet.MoveFirst
   If recTablDet!ID <> lID Then
      recTablDet.Find "ID = '" & lID & "'"
   End If
   
   'открываем форму
   bolYes = False
   FormDetailEdit.Show
   If bolYes = False Then
      'нажали отмену
      Exit Sub
   End If
   
   'редактируем запись в базе (возможно дублирование будет)
   recTablDet!Name = FormDetailEdit.TextBoxName
   recTablDet!Massa = CDbl(FormDetailEdit.TextBoxMassa)
   recTablDet!Naimen = FormDetailEdit.TextBoxNaimen
   If ComboBoxTables = "Наши изделия" Then
      recTablDet!Obozn = FormDetailEdit.ComboBoxObozn
      recTablDet!Type = FormDetailEdit.ComboBoxSer
   ElseIf ComboBoxTables = "Типовые" Then
      recTablDet!Obozn = FormDetailEdit.ComboBoxObozn
   Else
      recTablDet!Obozn = FormDetailEdit.TextBoxObozn
   End If
   recTablDet!Примечание = FormDetailEdit.TextBoxPrimech
   recTablDet.Update
   'возможна ошибка при дублировании имени изделия
   'в таком случае выдаем сообщение и возвращаем в форму FormDetailEdit для исправления
   'по хорошему надо роазать где уже есть эта деталь и в каких узлах она используется
   
   'если все ок, добавляем запись в листвиевер
   ListBoxTableDetails.List(0, 0) = recTablDet!Name
   ListBoxTableDetails.List(0, 1) = recTablDet!Obozn
   ListBoxTableDetails.List(0, 2) = recTablDet!Massa
   ListBoxTableDetails.List(0, 3) = recTablDet!Naimen
   ListBoxTableDetails.List(0, 4) = recTablDet!Type
   ListBoxTableDetails.List(0, 6) = recTablDet!Примечание
   
Exit Sub

HasError:
   Select Case Err.Number
      Case -2147217887
         'дублирование записей
         'точно:"Изменения не были успешно внесены из-за повторяющихся значений в индексе, ключевых полях или связях.  Измените данные в поле или полях, содержащих повторяющиеся значения, удалите индекс или переопределите его, чтобы разрешить повторяющиеся значения, и п"
         MsgBox "Такая деталь уже есть", vbCritical, pcsVBProjectName
'         recTablDet.Requery
      Case Else
         MsgBox "FormDetails, cmbDetailAdd_Click" & vbCrLf & _
               Err.Description, vbCritical, pcsVBProjectName
'         recTablDet.Requery
   End Select
   
End Sub

Private Sub cmbExit_Click()
   bolYes = False
   Hide
End Sub

Private Sub cmbOK_Click()
   bolYes = True
   Hide
End Sub

Private Sub cmdRefresh_Click()
   
   recTablDet.Requery
   ComboBoxTables_Change
   
End Sub

Private Sub ComboBoxFilterAlbom_Change()
   'фильтр издклий по альбому
   
   Dim strSql As String
   Dim strValue As String
   Dim intValue As Integer
   
   On Error GoTo HasError
   
   If ComboBoxFilterAlbom = "" Then Exit Sub
   
   Select Case ComboBoxTables
      Case "Наши изделия"
         If ComboBoxFilterAlbom = "Все" Then
            strSql = "SELECT * FROM Изделия WHERE Type ='" & ComboBoxFilterSer & "'  ORDER BY Name;"
         Else
            strSql = "SELECT * FROM Изделия WHERE Obozn = '" & ComboBoxFilterAlbom & "' ORDER BY Name;"
         End If
      Case "Пластины"
         strSql = "SELECT * FROM Изделия WHERE Type ='Пластины' ORDER BY Name;"
   End Select
   
   'очищзаем листвиевер деталей
   'ListViewTablDetails.ListItems.Clear
   ListBoxTableDetails.Clear
   
   'закрываем рексет
   If recTablDet.State = adStateOpen Then
      recTablDet.Close
   End If
   
   'создаем рекордсет
   recTablDet.Open Source:=strSql, ActiveConnection:=objConect, _
            CursorType:=adOpenKeyset, LockType:=adLockOptimistic, Options:=adCmdText
   If recTablDet.EOF And recTablDet.BOF Then Exit Sub
   recTablDet.MoveFirst
   Select Case ComboBoxTables
      Case "Наши изделия"
         Do Until recTablDet.EOF
            'Set objListItem = ListViewTablDetails.ListItems.Add(, , recTablDet!Name)
            ListBoxTableDetails.AddItem recTablDet!Name, 0
            ListBoxTableDetails.List(0, 1) = recTablDet!Obozn
            ListBoxTableDetails.List(0, 2) = recTablDet!Massa
            ListBoxTableDetails.List(0, 3) = recTablDet!Naimen
            ListBoxTableDetails.List(0, 4) = recTablDet!Type
            ListBoxTableDetails.List(0, 5) = recTablDet!ID
            If IsNull(recTablDet!Примечание) = True Then
               ListBoxTableDetails.List(0, 6) = ""
            Else
               ListBoxTableDetails.List(0, 6) = recTablDet!Примечание
            End If
            recTablDet.MoveNext
         Loop
      Case "Пластины"
         'нужно отобрать только пластины с заданной толщиной и шириной
         Do Until recTablDet.EOF
            If ComboBoxFilterAlbom = "Все" Then
               'скрываем этот комбобокс а в первом делает имитацию клика
               ComboBoxFilterSer_Change
               Exit Sub
            Else
               If Val(recTablDet!Name) = ComboBoxFilterSer Then
                  intValue = InStr(recTablDet!Name, "x")
                  strValue = VBA.Mid(recTablDet!Name, intValue + 1)
                  If Val(strValue) <> ComboBoxFilterAlbom Then
                     GoTo Sled
                  End If
               Else
                  GoTo Sled
               End If
            End If
            
'            Set objListItem = ListViewTablDetails.ListItems.Add(, , recTablDet!Name)
'            objListItem.SubItems(1) = recTablDet!Obozn
'            objListItem.SubItems(2) = recTablDet!Massa
'            objListItem.SubItems(3) = recTablDet!Naimen
'            objListItem.SubItems(4) = recTablDet!Type
'            objListItem.SubItems(5) = recTablDet!ID
            ListBoxTableDetails.AddItem recTablDet!Name, 0
            ListBoxTableDetails.List(0, 1) = recTablDet!Obozn
            ListBoxTableDetails.List(0, 2) = recTablDet!Massa
            ListBoxTableDetails.List(0, 3) = recTablDet!Naimen
            ListBoxTableDetails.List(0, 4) = recTablDet!Type
            ListBoxTableDetails.List(0, 5) = recTablDet!ID
            If IsNull(recTablDet!Примечание) = True Then
               ListBoxTableDetails.List(0, 6) = ""
            Else
               ListBoxTableDetails.List(0, 6) = recTablDet!Примечание
            End If
Sled:
            recTablDet.MoveNext
         Loop
   End Select

Exit Sub
HasError:
   MsgBox Err.Description, vbCritical, pcsVBProjectName
   
End Sub

Private Sub ComboBoxFilterSer_Change()
   'фильтр изделий по серии
   
   Dim strSql As String
   
   On Error GoTo HasError
   
   If ComboBoxFilterSer = "" Then Exit Sub
   
   Select Case ComboBoxTables
      Case "Наши изделия"
         If ComboBoxFilterSer = "Все" Then
            'запрос всех наших изделий
            If bolEditOrAdd = True Then
               strSql = "SELECT * FROM Изделия WHERE Type NOT IN ('Стержни', 'Уголки', 'Пластины', 'Типовые') ORDER BY Name;"
            Else
               strSql = "SELECT * FROM Изделия WHERE Type in '" & FormNodes.ComboBoxSer & "' ORDER BY Name;"
            End If
         Else
            strSql = "SELECT * FROM Изделия WHERE Type = '" & ComboBoxFilterSer & "' ORDER BY Name;"
         End If
      Case "Типовые"
         If ComboBoxFilterSer = "Все" Then
            strSql = "SELECT * FROM Изделия WHERE Type = 'Типовые' ORDER BY Name;"
         Else
            strSql = "SELECT * FROM Изделия WHERE Obozn = '" & ComboBoxFilterSer & "' ORDER BY Name;"
         End If
      Case "Пластины"
         strSql = "SELECT * FROM Изделия WHERE Type ='Пластины' ORDER BY Name;"
      Case "Стержни"
         strSql = "SELECT * FROM Изделия WHERE Type ='Стержни' ORDER BY Name;"
      Case Else
         Exit Sub
   End Select
   
   'очищзаем листвиевер деталей
   'ListViewTablDetails.ListItems.Clear
   ListBoxTableDetails.Clear
   
   'закрываем рексет
   If recTablDet.State = adStateOpen Then recTablDet.Close
   'создаем рекордсет
   recTablDet.Open Source:=strSql, ActiveConnection:=objConect, _
            CursorType:=adOpenKeyset, LockType:=adLockOptimistic, Options:=adCmdText
   If recTablDet.EOF And recTablDet.BOF Then
      GoTo Filter2
   End If
   
   recTablDet.MoveFirst
   Select Case ComboBoxTables
      Case "Наши изделия"
         Do Until recTablDet.EOF
            'Set objListItem = ListViewTablDetails.ListItems.Add(, , recTablDet!Name)
            ListBoxTableDetails.AddItem recTablDet!Name, 0
            ListBoxTableDetails.List(0, 1) = recTablDet!Obozn
            ListBoxTableDetails.List(0, 2) = recTablDet!Massa
            ListBoxTableDetails.List(0, 3) = recTablDet!Naimen
            ListBoxTableDetails.List(0, 4) = recTablDet!Type
            ListBoxTableDetails.List(0, 5) = recTablDet!ID
            If IsNull(recTablDet!Примечание) = True Then
               ListBoxTableDetails.List(0, 6) = ""
            Else
               ListBoxTableDetails.List(0, 6) = recTablDet!Примечание
            End If
            recTablDet.MoveNext
         Loop
      Case "Типовые"
         Do Until recTablDet.EOF
            'Set objListItem = ListViewTablDetails.ListItems.Add(, , recTablDet!Name)
            ListBoxTableDetails.AddItem recTablDet!Name, 0
            ListBoxTableDetails.List(0, 1) = recTablDet!Obozn
            ListBoxTableDetails.List(0, 2) = recTablDet!Massa
            ListBoxTableDetails.List(0, 3) = recTablDet!Naimen
            ListBoxTableDetails.List(0, 4) = recTablDet!Type
            ListBoxTableDetails.List(0, 5) = recTablDet!ID
            If IsNull(recTablDet!Примечание) = True Then
               ListBoxTableDetails.List(0, 6) = ""
            Else
               ListBoxTableDetails.List(0, 6) = recTablDet!Примечание
            End If
            recTablDet.MoveNext
         Loop
      Case "Пластины"
         Do Until recTablDet.EOF
            If ComboBoxFilterSer <> "Все" Then
               If Val(recTablDet!Name) <> ComboBoxFilterSer Then
                  GoTo SledList
               End If
            End If
                ListBoxTableDetails.AddItem recTablDet!Name, 0
                ListBoxTableDetails.List(0, 1) = recTablDet!Obozn
                ListBoxTableDetails.List(0, 2) = recTablDet!Massa
                ListBoxTableDetails.List(0, 3) = recTablDet!Naimen
                ListBoxTableDetails.List(0, 4) = recTablDet!Type
                ListBoxTableDetails.List(0, 5) = recTablDet!ID
               If IsNull(recTablDet!Примечание) = True Then
                  ListBoxTableDetails.List(0, 6) = ""
               Else
                  ListBoxTableDetails.List(0, 6) = recTablDet!Примечание
               End If
SledList:
            recTablDet.MoveNext
         Loop
      Case "Стержни"
         Do Until recTablDet.EOF
            If ComboBoxFilterSer <> "Все" Then
               If Val(recTablDet!Name) <> ComboBoxFilterSer Then
                  GoTo SledSterg
               End If
            End If
               'Set objListItem = ListViewTablDetails.ListItems.Add(, , recTablDet!Name)
               ListBoxTableDetails.AddItem recTablDet!Name, 0
                ListBoxTableDetails.List(0, 1) = recTablDet!Obozn
                ListBoxTableDetails.List(0, 2) = recTablDet!Massa
                ListBoxTableDetails.List(0, 3) = recTablDet!Naimen
                ListBoxTableDetails.List(0, 4) = recTablDet!Type
                ListBoxTableDetails.List(0, 5) = recTablDet!ID
               If IsNull(recTablDet!Примечание) = True Then
                  ListBoxTableDetails.List(0, 6) = ""
               Else
                  ListBoxTableDetails.List(0, 6) = recTablDet!Примечание
               End If
SledSterg:
            recTablDet.MoveNext
         Loop
   End Select

Filter2:
   Dim asFilter2 As Variant
   Dim asName() As String
   Dim i As Integer
   'заполняем комбобокс фильтра альбомов
   ComboBoxFilterAlbom.Clear
   If ListBoxTableDetails.ListCount = 0 Then Exit Sub
   Select Case ComboBoxTables
      Case "Наши изделия"
         If ComboBoxFilterSer = "Все" Then
            'скрываем фильтр по альбомам
            ComboBoxFilterAlbom.Enabled = False
'            ComboBoxTables_Change
         Else
            ComboBoxFilterAlbom.Enabled = True
            strSql = "SELECT Изделия.Obozn FROM Изделия WHERE Type = '" & ComboBoxFilterSer & "' GROUP BY Obozn ORDER BY Obozn;"
            'создаем рекордсет
            If recSet.State = adStateOpen Then recSet.Close
            recSet.Open Source:=strSql, ActiveConnection:=objConect, _
                     CursorType:=adOpenKeyset, LockType:=adLockOptimistic, Options:=adCmdText
            recSet.MoveFirst
            Do Until recSet.EOF
               ComboBoxFilterAlbom.AddItem recSet!Obozn
               recSet.MoveNext
            Loop
            ComboBoxFilterAlbom.AddItem "Все"
         End If
      Case "Пластины"
         If ComboBoxFilterSer = "Все" Then
            'скрываем фильтр по альбомам
            ComboBoxFilterAlbom.Enabled = False
            ComboBoxTables_Change
         Else
            ComboBoxFilterAlbom.Enabled = True
            'получение массива ширин из имени пластин вида 8x30x60
            recTablDet.MoveFirst
            Do Until recTablDet.EOF
               If Val(recTablDet!Name) = ComboBoxFilterSer Then
                  ReDim Preserve asName(i)
                  asName(i) = recTablDet!Name
                  i = i + 1
               End If
               recTablDet.MoveNext
            Loop
            asFilter2 = Funcions.GetWidthFromListName(asName)
            'заполнение комбобокса фильтра толщин пластин
            For i = 0 To UBound(asFilter2)
               ComboBoxFilterAlbom.AddItem asFilter2(i)
            Next
            ComboBoxFilterAlbom.AddItem "Все"
         End If
   End Select
   
Exit Sub
HasError:
   MsgBox Err.Description, vbCritical, pcsVBProjectName
      
End Sub

Private Sub ComboBoxTables_Change()
   'заполняем листвиевер выбранным типом изделий
   
   Dim strSql As String
   Dim index As Integer
   
   On Error GoTo HasError
   
   index = ComboBoxTables.ListIndex
   If index = -1 Then
      Exit Sub
   End If
   
   'ListViewTablDetails.ListItems.Clear
   ListBoxTableDetails.Clear
   
   'если вибрали наши изделия то запрос удет такой
   Select Case ComboBoxTables
      Case "Наши изделия"
         'запрос всех изделий по всем альбомам наших изделий
   '      strCurSer = "All" 'т.е. не выбрана серия
         If bolEditOrAdd = True Then
            strSql = "SELECT * FROM Изделия WHERE Type NOT IN ('Стержни', 'Уголки', 'Пластины', 'Типовые') ORDER BY Name;"
         Else
            strSql = "SELECT * FROM Изделия WHERE Type = '" & FormNodes.ComboBoxSer & "' ORDER BY Name;"
         End If
         LabelFilter2.Visible = True
         LabelFilter1.Visible = True
         LabelFilter1.Enabled = True
         LabelFilter2.Enabled = True
         ComboBoxFilterAlbom.Visible = True
         ComboBoxFilterSer.Visible = True
         ComboBoxFilterAlbom.Enabled = False
         ComboBoxFilterSer.Enabled = True
         ComboBoxFilterAlbom.Clear
         ComboBoxFilterSer.Clear
         LabelFilter1 = "Фильтр по серии:"
         LabelFilter2 = "Фильтр по альбому:"
      Case "Пластины"
         strSql = "SELECT * FROM Изделия WHERE Type = '" & ComboBoxTables & "' ORDER BY Name;"
         LabelFilter1.Visible = True
         LabelFilter2.Visible = True
         LabelFilter1.Enabled = True
         LabelFilter2.Enabled = True
         ComboBoxFilterAlbom.Visible = True
         ComboBoxFilterSer.Visible = True
         ComboBoxFilterSer.Enabled = True
         ComboBoxFilterAlbom.Enabled = False
         ComboBoxFilterAlbom.Clear
         ComboBoxFilterSer.Clear
         LabelFilter1 = "Фильтр по толщине:"
         LabelFilter2 = "Фильтр по ширине:"
      Case "Стержни"
         strSql = "SELECT * FROM Изделия WHERE Type = '" & ComboBoxTables & "' ORDER BY Name;"
         LabelFilter1.Visible = True
         LabelFilter2.Visible = False
         LabelFilter1.Enabled = True
         ComboBoxFilterAlbom.Visible = False
         ComboBoxFilterSer.Visible = True
         ComboBoxFilterSer.Enabled = True
         ComboBoxFilterSer.Clear
         LabelFilter1 = "Фильтр по диаметру:"
         LabelFilter2 = "Фильтр по ширине:"
      Case "Типовые"
         strSql = "SELECT * FROM Изделия WHERE Type = '" & ComboBoxTables & "' ORDER BY Name;"
         'заносим фильтр по типовым альбомам
         LabelFilter1.Visible = True
         LabelFilter2.Visible = False
         LabelFilter1.Enabled = True
         ComboBoxFilterAlbom.Visible = False
         ComboBoxFilterSer.Visible = True
         ComboBoxFilterSer.Enabled = True
         ComboBoxFilterSer.Clear
         LabelFilter1 = "Фильтр по альбому:"
      Case Else
         'запрос для остальых типов детаей
         strSql = "SELECT * FROM Изделия WHERE Type = '" & ComboBoxTables & "' ORDER BY Name;"
         LabelFilter1.Visible = False
         LabelFilter2.Visible = False
         ComboBoxFilterAlbom.Visible = False
         ComboBoxFilterSer.Visible = False
   End Select
   
   If recTablDet.State = adStateOpen Then
      recTablDet.Close
   End If
   
   'создаем рекордсет
   recTablDet.Open Source:=strSql, ActiveConnection:=objConect, _
            CursorType:=adOpenKeyset, LockType:=adLockOptimistic, Options:=adCmdText
   If recTablDet.EOF And recTablDet.BOF Then
      MsgBox "В этой серии пока нет деталей!", vbInformation, pcsVBProjectName
      Exit Sub
   End If
   'выводим данные в листвевер
   recTablDet.MoveFirst
   Do Until recTablDet.EOF
      'заносим данные этой записи
      'Set objListItem = ListViewTablDetails.ListItems.Add(, , recTablDet!Name)
      ListBoxTableDetails.AddItem recTablDet!Name, 0
      ListBoxTableDetails.List(0, 1) = recTablDet!Obozn
      ListBoxTableDetails.List(0, 2) = recTablDet!Massa
      ListBoxTableDetails.List(0, 3) = recTablDet!Naimen
      ListBoxTableDetails.List(0, 4) = recTablDet!Type
      ListBoxTableDetails.List(0, 5) = recTablDet!ID
      If IsNull(recTablDet!Примечание) = True Then
         ListBoxTableDetails.List(0, 6) = ""
      Else
         ListBoxTableDetails.List(0, 6) = recTablDet!Примечание
      End If
      recTablDet.MoveNext
   Loop
   
   Dim asName() As String
   Dim asFilter1 As Variant
   Dim i As Integer
   'если выбранв Наши изделия, заполняем комбобоксы фильтров
   Select Case ComboBoxTables
      Case "Наши изделия"
         'запрос всех серий в таблице альбомов
         If recSet.State = adStateOpen Then recSet.Close
         If bolEditOrAdd = True Then
            'все серии
            strSql = "SELECT Ser FROM Серии WHERE Ser <> 'Типовые' GROUP BY Ser ORDER BY Ser"
            recSet.Open Source:=strSql, ActiveConnection:=objConect, _
               CursorType:=adOpenStatic, LockType:=adLockReadOnly, Options:=adCmdText
            recSet.MoveFirst
            Do Until recSet.EOF
               ComboBoxFilterSer.AddItem recSet!Ser
               recSet.MoveNext
            Loop
               ComboBoxFilterSer.AddItem "Все"
         Else
            'только текущая
            ComboBoxFilterSer.AddItem FormNodes.ComboBoxSer
'            strSQL = "SELECT Ser FROM Серии WHERE Ser = '" & FormNodes.ComboBoxSer & "'"
         End If
         LabelFilter1 = "Фильтр по серии:"
      Case "Типовые"
'         strSQL = "SELECT Obozn FROM Альбомы WHERE Альбомы.Ser_ID = Серии.ID AND Серии.Ser = 'Типовые' GROUP BY Obozn ORDER Obozn BY "
         strSql = "SELECT Альбомы.Obozn FROM Серии INNER JOIN Альбомы ON Серии.ID = Альбомы.Ser_ID Where Серии.Ser = 'Типовые'"
         If recSet.State = adStateOpen Then recSet.Close
         recSet.Open Source:=strSql, ActiveConnection:=objConect, _
            CursorType:=adOpenStatic, LockType:=adLockReadOnly, Options:=adCmdText
         recSet.MoveFirst
         Do Until recSet.EOF
            ComboBoxFilterSer.AddItem recSet!Obozn
            recSet.MoveNext
         Loop
         ComboBoxFilterSer.AddItem "Все"
      Case "Пластины"
         'запрос всех пластин в таблице изделий
         If recSet.State = adStateOpen Then recSet.Close
         strSql = "SELECT Name FROM Изделия WHERE Type = 'Пластины' ORDER BY Name"
         recSet.Open Source:=strSql, ActiveConnection:=objConect, _
               CursorType:=adOpenStatic, LockType:=adLockReadOnly, Options:=adCmdText
         recSet.MoveFirst
         Do Until recSet.EOF
            ReDim Preserve asName(i)
            asName(i) = recSet!Name
            i = i + 1
            recSet.MoveNext
         Loop
         'получение массива толщин из имени пластин вида 8x30x60
         asFilter1 = Funcions.GetTfromListName(asName)
         'заполнение комбобокса фильтра толщин пластин
         For i = 0 To UBound(asFilter1)
            ComboBoxFilterSer.AddItem asFilter1(i)
         Next
         ComboBoxFilterSer.AddItem "Все"
      Case "Стержни"
         'запрос всех cnth;ytq в таблице изделий
         If recSet.State = adStateOpen Then recSet.Close
         strSql = "SELECT Name FROM Изделия WHERE Type = 'Стержни' ORDER BY Name"
         recSet.Open Source:=strSql, ActiveConnection:=objConect, _
               CursorType:=adOpenStatic, LockType:=adLockReadOnly, Options:=adCmdText
         recSet.MoveFirst
         Do Until recSet.EOF
            ReDim Preserve asName(i)
            asName(i) = recSet!Name
            i = i + 1
            recSet.MoveNext
         Loop
         'получение массива диаметров из имени пластин вида 8x30x60
         asFilter1 = Funcions.GetTfromListName(asName)
         'заполнение комбобокса фильтра толщин пластин
         For i = 0 To UBound(asFilter1)
            ComboBoxFilterSer.AddItem asFilter1(i)
         Next
         ComboBoxFilterSer.AddItem "Все"
   End Select
   
Exit Sub
HasError:
   MsgBox Err.Description, vbCritical, pcsVBProjectName
   
End Sub


'Private Sub ListViewTablDetails_ColumnClick(ByVal ColumnHeader As MSComctlLib.ColumnHeader)
'   'сортируем по столбцу
'
'   If ListViewTablDetails.SortOrder = lvwAscending Then
'      ListViewTablDetails.SortOrder = lvwDescending
'   Else
'      ListViewTablDetails.SortOrder = lvwAscending
'   End If
'
'   ListViewTablDetails.SortKey = ColumnHeader.index - 1
'
'End Sub

'Private Sub ListViewTablDetails_ItemClick(ByVal Item As MSComctlLib.ListItem)
'
'   Dim objListItem As ListItem
'
'   Set objListItem = ListViewTablDetails.SelectedItem
'   If objListItem Is Nothing Then Exit Sub
'   'выводим строку примечание
'   LabelPrimech = objListItem.SubItems(6)
'
''******* запрос узлов в состав которых входит данная деталь *********
'   Dim sSql As String
'   Dim asSer() As String
'   Dim intCount As Integer
'   Dim sngID As Single
'
'   sngID = objListItem.SubItems(5)
''   'запрос во всех сериях
''   'запрос серий
''   If recSet.State = adStateOpen Then recSet.Close
''   sSQL = "SELECT Ser FROM Серии;"
''   recSet.Open Source:=sSQL, ActiveConnection:=objConect, _
''         CursorType:=adOpenStatic, LockType:=adLockReadOnly, Options:=adCmdText
''   If recSet.EOF And recSet.BOF Then Exit Sub
''   recSet.MoveFirst
''   intCount = 0
''   'запись серий в массив
''   Do Until recSet.EOF
''      ReDim Preserve asSer(intCount)
''      asSer(intCount) = recSet!Ser
''      intCount = intCount + 1
''      recSet.MoveNext
''   Loop
'
'   ListBoxNodes.Clear
''   For intCount = 0 To UBound(asSer)
'      'запрос узлов в которых есть Detail_ID из таблицы Узлов
'      sSql = "SELECT Узлы.Name, Узлы.Obozn " & _
'            "FROM Узлы INNER JOIN Состав ON Узлы.ID = Состав.Node_ID " & _
'            "WHERE Состав.Detail_ID = " & sngID & " " & _
'            "ORDER BY Узлы.Name DESC;"
'      If recSet.State = adStateOpen Then recSet.Close
'      recSet.Open Source:=sSql, ActiveConnection:=objConect, _
'         CursorType:=adOpenStatic, LockType:=adLockReadOnly, Options:=adCmdText
'      If Not recSet.EOF And Not recSet.BOF Then
'         recSet.MoveFirst
'         Do Until recSet.EOF
'            ListBoxNodes.AddItem recSet!Name & ", " & recSet!Obozn
'            recSet.MoveNext
'         Loop
'      End If
'
'      'запрос узлов в которых есть Detail_ID из таблицы Типовые_узлы
'      sSql = "SELECT Типовые_узлы.Name, Типовые_узлы.Obozn " & _
'            "FROM Типовые_узлы INNER JOIN Типовые_состав ON Типовые_узлы.ID = Типовые_состав.Node_ID " & _
'            "WHERE Типовые_состав.Detail_ID = " & sngID & " " & _
'            "ORDER BY Типовые_узлы.Name DESC;"
'      If recSet.State = adStateOpen Then recSet.Close
'      recSet.Open Source:=sSql, ActiveConnection:=objConect, _
'         CursorType:=adOpenStatic, LockType:=adLockReadOnly, Options:=adCmdText
'      If Not recSet.EOF And Not recSet.BOF Then
'         recSet.MoveFirst
'         Do Until recSet.EOF
'            ListBoxNodes.AddItem recSet!Name & ", " & recSet!Obozn
'            recSet.MoveNext
'         Loop
'      End If
''   Next
''********* конец узлов в состав которых входит данная деталь *********
'
'End Sub

Private Sub ListBoxTableDetails_Click()
  Dim index As Integer
   
   index = ListBoxTableDetails.ListIndex
   'Set objListItem = ListViewTablDetails.SelectedItem
   If index = -1 Then Exit Sub
   'выводим строку примечание
   LabelPrimech = ListBoxTableDetails.List(index, 6) '   objListItem.SubItems(6)
   
'******* запрос узлов в состав которых входит данная деталь *********
   Dim sSql As String
   Dim asSer() As String
   Dim intCount As Integer
   Dim sngID As Single
   
   sngID = ListBoxTableDetails.List(index, 5) 'objListItem.SubItems(5)
'   'запрос во всех сериях
'   'запрос серий
'   If recSet.State = adStateOpen Then recSet.Close
'   sSQL = "SELECT Ser FROM Серии;"
'   recSet.Open Source:=sSQL, ActiveConnection:=objConect, _
'         CursorType:=adOpenStatic, LockType:=adLockReadOnly, Options:=adCmdText
'   If recSet.EOF And recSet.BOF Then Exit Sub
'   recSet.MoveFirst
'   intCount = 0
'   'запись серий в массив
'   Do Until recSet.EOF
'      ReDim Preserve asSer(intCount)
'      asSer(intCount) = recSet!Ser
'      intCount = intCount + 1
'      recSet.MoveNext
'   Loop

   ListBoxNodes.Clear
'   For intCount = 0 To UBound(asSer)
      'запрос узлов в которых есть Detail_ID из таблицы Узлов
      sSql = "SELECT Узлы.Name, Узлы.Obozn " & _
            "FROM Узлы INNER JOIN Состав ON Узлы.ID = Состав.Node_ID " & _
            "WHERE Состав.Detail_ID = " & sngID & " " & _
            "ORDER BY Узлы.Name DESC;"
      If recSet.State = adStateOpen Then recSet.Close
      recSet.Open Source:=sSql, ActiveConnection:=objConect, _
         CursorType:=adOpenStatic, LockType:=adLockReadOnly, Options:=adCmdText
      If Not recSet.EOF And Not recSet.BOF Then
         recSet.MoveFirst
         Do Until recSet.EOF
            ListBoxNodes.AddItem recSet!Name & ", " & recSet!Obozn
            recSet.MoveNext
         Loop
      End If
      
      'запрос узлов в которых есть Detail_ID из таблицы Типовые_узлы
      sSql = "SELECT Типовые_узлы.Name, Типовые_узлы.Obozn " & _
            "FROM Типовые_узлы INNER JOIN Типовые_состав ON Типовые_узлы.ID = Типовые_состав.Node_ID " & _
            "WHERE Типовые_состав.Detail_ID = " & sngID & " " & _
            "ORDER BY Типовые_узлы.Name DESC;"
      If recSet.State = adStateOpen Then recSet.Close
      recSet.Open Source:=sSql, ActiveConnection:=objConect, _
         CursorType:=adOpenStatic, LockType:=adLockReadOnly, Options:=adCmdText
      If Not recSet.EOF And Not recSet.BOF Then
         recSet.MoveFirst
         Do Until recSet.EOF
            ListBoxNodes.AddItem recSet!Name & ", " & recSet!Obozn
            recSet.MoveNext
         Loop
      End If
'   Next
'********* конец узлов в состав которых входит данная деталь *********
End Sub

Private Sub UserForm_Activate()
   'определяем каталог открыть для просмотра/редактирования или для добавления детали
   
   'вставляем значения в комбобокс
   ComboBoxTables.Clear
   
   'ListViewTablDetails.ListItems.Clear
   ListBoxTableDetails.Clear
   
   If Me.Caption = "Каталог деталей" Then
      bolEditOrAdd = True 'значит для просмотра
      ComboBoxTables.AddItem "Наши изделия"
   Else
      'значит для добавления детали
      bolEditOrAdd = False
      'тут есть зависимость от типа серии в которую добавляется деталь
      'если типовая, то в нее нельзя добавить деталь из наших серий
      If FormNodes.ComboBoxSer <> "Типовые" Then
         ComboBoxTables.AddItem "Наши изделия"
      End If
   End If
   'добавляем остальные типы деталей в комбобокс, они используются во всех сериях.
   ComboBoxTables.AddItem "Стержни"
   ComboBoxTables.AddItem "Уголки"
   ComboBoxTables.AddItem "Пластины"
   ComboBoxTables.AddItem "Типовые"
   
   'скрываем фильтры, пока не выбран тип в комбобоксе
   ComboBoxFilterAlbom.Enabled = False
   ComboBoxFilterSer.Enabled = False
   
End Sub

Private Sub UserForm_Initialize()
   
   'вставляем столбцы в листвиевер
'   ListViewTablDetails.ColumnHeaders.Add , "Name", "Имя", 60
'   ListViewTablDetails.ColumnHeaders.Add , "Obozn", "Обозначение", 80
'   ListViewTablDetails.ColumnHeaders.Add , "Massa", "Масса", 50
'   ListViewTablDetails.ColumnHeaders.Add , "Naimen", "Наименование", 120
'   ListViewTablDetails.ColumnHeaders.Add , "Type", "Тип", 25
'   ListViewTablDetails.ColumnHeaders.Add , "ID", "ID", 25
'   ListViewTablDetails.ColumnHeaders.Add , "Prim", "Примечание", 25
      
End Sub

Private Sub UserForm_QueryClose(Cancel As Integer, CloseMode As Integer)
   
   bolYes = False
   Hide
   
End Sub

Attribute VB_Name = "FormInsNode"
Attribute VB_Base = "0{B0A631FE-CF1F-4190-AF81-78E3D5F07A75}{ED449AAC-1351-4288-8289-D9A9DA4C4669}"
Attribute VB_GlobalNameSpace = False
Attribute VB_Creatable = False
Attribute VB_PredeclaredId = True
Attribute VB_Exposed = False
Attribute VB_TemplateDerived = False
Attribute VB_Customizable = False
Option Explicit

Dim bFormIsMadal As Boolean

Dim dLeft As Double
Dim dTop As Double


Private Sub cmbExit_Click()
   End
End Sub

Private Sub cmbInsert_Click()
   'вставка выбранного блока в чертеж
   
   Dim strNodeDWGFullPath As String
   Dim dM As Double
   
   On Error GoTo HasError
   
   If ListBoxNodes.ListIndex = -1 Then
      MsgBox "Не выбран узел!", vbCritical, pcsVBProjectName
      Exit Sub
   End If
   
   strNodeDWGFullPath = Funcions.GetMacroFolder(pcsVBProjectName) & "\Блоки\Узел.dwg"
   
   If Dir(strNodeDWGFullPath) = "" Then
      MsgBox "Не найден файл - " & strNodeDWGFullPath, vbCritical, pcsVBProjectName
      Exit Sub
   End If
   
   ThisDrawing.ActiveLayer.LayerOn = True
   ThisDrawing.ActiveLayer.Lock = False
   
   dM = FormSer.TextBoxM
   
   If CheckBoxMulty.Value = True Then
      Do
         InsertBlNode strNodeDWGFullPath, dM
      Loop While True
   Else
      InsertBlNode strNodeDWGFullPath, dM
   End If
   
Exit Sub

HasError:
   Select Case Err.Number
      Case -2147352567 'Automatiom error
         'нажали ескейп при множественной вставке блока
      Case Else
         MsgBox Err.Description, vbCritical, pcsVBProjectName
   End Select
   
End Sub

Private Sub InsertBlNode(strNodeDWGFullPath As String, dM As Double)
   Dim objBlNode As AcadBlockReference
   Dim varPt As Variant
   Dim varAtr As Variant
   Dim objAtr As AcadAttributeReference
   Dim index As Integer
   
   index = ListBoxNodes.ListIndex
   
   varPt = ThisDrawing.Utility.GetPoint(, "Точка вставки")
   Set objBlNode = ThisDrawing.ModelSpace.InsertBlock(varPt, strNodeDWGFullPath, dM, dM, 1, 0)
   objBlNode.Layer = "Блоки узлов"
   'назначаем значение атрибуту
   For Each varAtr In objBlNode.GetAttributes
      Set objAtr = varAtr
      Select Case VBA.LCase(objAtr.TagString)
         Case "марка"
            objAtr.TextString = ListBoxNodes.Text
         Case "обозначение"
            objAtr.TextString = ListBoxNodes.List(index, 1)
      End Select
   Next
   
End Sub

Private Sub ComboBoxObozn_Change()
   'запрос узлов для выбранного альбома
   
   Dim objRecSet As New ADODB.Recordset
   Dim strSql As String
   Dim strSer As String
   Dim index As Integer
   Dim i As Integer
   
   On Error GoTo HasError
   
   index = ComboBoxObozn.ListIndex
   
   ListBoxNodes.Clear
   
   If ComboBoxObozn = "Все" Then
      'все узлы по серии и типовые
      strSql = "SELECT Name, Obozn FROM Узлы " & _
         "Union Select Name, Obozn From Типовые_узлы " & _
         "Order by Name;"
   Else
      strSer = ComboBoxObozn.List(index, 1)
      'запрос узлов по выбранному обозначению
      strSql = "SELECT Name, Obozn FROM Узлы " & _
            "WHERE Узлы.Obozn = '" & ComboBoxObozn & "' " & _
            "Union Select Name, Obozn From Типовые_узлы " & _
            "WHERE Типовые_узлы.Obozn = '" & ComboBoxObozn & "' ORDER BY Name;"
   End If
   objRecSet.Open Source:=strSql, ActiveConnection:=objConect, _
            CursorType:=adOpenKeyset, LockType:=adLockOptimistic, Options:=adCmdText
   If objRecSet.EOF And objRecSet.BOF Then
      MsgBox "Нет узлов! Создайте узлы в каталоге узлов!", vbCritical, pcsVBProjectName
      Exit Sub
   End If
   
   i = 0
   objRecSet.MoveFirst
   Do Until objRecSet.EOF
      ListBoxNodes.AddItem objRecSet!Name, i
      ListBoxNodes.List(i, 1) = objRecSet!Obozn
      objRecSet.MoveNext
      i = i + 1
   Loop
   
Exit Sub
HasError:
   MsgBox Err.Description, vbCritical, pcsVBProjectName
   
End Sub

Private Sub TextBoxM_Change()
   'переводим форму в не модальный режим
   Hide
   FormInsNode.Show vbModeless
End Sub

Private Sub TextBoxM_Enter()
   'переводим форму в модальный режим
   
   Hide
   FormInsNode.Show
     
   TextBoxM.SetFocus
     
End Sub

Private Sub ListBoxNodes_Click()
   'записываем лайбл обозначения для выбранного узла
   Dim index As Integer
   index = ListBoxNodes.ListIndex
   If index = -1 Then Exit Sub
   LabelObozn = ListBoxNodes.List(index, 1)
End Sub

Private Sub TextBoxFilter_Change()
  'фильтруем список узлов этого обозначения
  
   Dim objRecSet As New ADODB.Recordset
   Dim strSql As String
   Dim strSer As String
   Dim index As Integer
   Dim i As Integer
   
   On Error GoTo HasError
   
   ListBoxNodes.Clear
   
   'если пустой фильтр, то выбираем то что выбрано в комбобоксе ComboBoxObozn
   If TextBoxFilter = "" Then
      ComboBoxObozn_Change
      Exit Sub
   End If
   
   index = ComboBoxObozn.ListIndex
   
   If ComboBoxObozn = "Все" Then
      'все узлы с фильтром
      strSql = "SELECT Name, Obozn FROM Узлы " & _
               "WHERE Name Like '" & TextBoxFilter & "%' " & _
               "Union Select Name, Obozn From Типовые_узлы " & _
               "WHERE Name Like '" & TextBoxFilter & "%' " & _
               "Order by Name;"
   Else
      strSer = ComboBoxObozn.List(index, 1)
      'запрос узлов по выбранному обозначению с фильтром
      strSql = "SELECT Name, Obozn FROM Узлы " & _
               "WHERE Name Like '" & TextBoxFilter & "%' " & _
               "AND Obozn = '" & ComboBoxObozn & "' " & _
               "Union Select Name, Obozn From Типовые_узлы " & _
               "WHERE Name Like '" & TextBoxFilter & "%' " & _
               "AND Obozn = '" & ComboBoxObozn & "' " & _
               "Order by Name;"
   End If
   
   objRecSet.Open Source:=strSql, ActiveConnection:=objConect, _
            CursorType:=adOpenKeyset, LockType:=adLockOptimistic, Options:=adCmdText
   If objRecSet.EOF And objRecSet.BOF Then
      Exit Sub
   End If
   
   i = 0
   objRecSet.MoveFirst
   Do Until objRecSet.EOF
      ListBoxNodes.AddItem objRecSet!Name, i
      ListBoxNodes.List(i, 1) = objRecSet!Obozn
      objRecSet.MoveNext
      i = i + 1
   Loop
   
Exit Sub
HasError:
   MsgBox Err.Description, vbCritical, pcsVBProjectName
  
End Sub

Private Sub TextBoxFilter_Enter()
  'сделать форму модальной
  
  'запись координат формы
  dLeft = Me.Left
  dTop = Me.top
  
  Me.Hide
  Me.Show vbModal
End Sub

Private Sub TextBoxFilter_Exit(ByVal Cancel As MSForms.ReturnBoolean)
  'сделать форму немодальной
  'запись координат формы
  dLeft = Me.Left
  dTop = Me.top
  
  Me.Hide
  Me.Show vbModeless
End Sub

Private Sub UserForm_Activate()
  'если записаны координаты, то применить их
  If dLeft <> 0 Then
    Me.Left = dLeft
    Me.top = dTop
  End If
End Sub

Private Sub UserForm_Click()

End Sub

Attribute VB_Name = "FormNodeEdit"
Attribute VB_Base = "0{B27CB408-88A7-4AFC-9884-C2D0D596DDF7}{146B5F59-D658-4478-8701-B6FB0746B256}"
Attribute VB_GlobalNameSpace = False
Attribute VB_Creatable = False
Attribute VB_PredeclaredId = True
Attribute VB_Exposed = False
Attribute VB_TemplateDerived = False
Attribute VB_Customizable = False
Option Explicit

Private Sub cmbDetailAdd_Click()
   'добавление детали из каталога деталей
   
   FormDetails.Caption = "Выбор изделия для добавления в состав узла " & TextBoxNode
   FormDetails.Show
   
End Sub

Private Sub cmbDetailEdit_Click()
   'активируем форму FormDetails
   
   'выделяем заданную деталь в листвеевере FormDetails.ListViewTablDetails
   
   'и пусть снбе редактирует
   'предупредить что изменение детали произойдет во всех узлах в которых есть эта деталь
   
End Sub

Attribute VB_Name = "FormNodes"
Attribute VB_Base = "0{1F754E21-5930-4ACC-BB08-551DC7DBAF74}{D43BF3E3-A257-425A-98D2-2F929DF24104}"
Attribute VB_GlobalNameSpace = False
Attribute VB_Creatable = False
Attribute VB_PredeclaredId = True
Attribute VB_Exposed = False
Attribute VB_TemplateDerived = False
Attribute VB_Customizable = False
Option Explicit

   Dim objRecSet As New ADODB.Recordset
   Dim objRecNodes As New ADODB.Recordset 'все узлы из таблицы узлов
   Dim objRecNodesDetail As New ADODB.Recordset 'Node_name,Detail_UniqName,Name,Range,Massa,Obozn,Naimen
   
Private Sub cmbAlbomAdd_Click()
   'добавление альбома в базу, в таблицу Альбомы
   
   Dim strSql As String
   Dim index As Integer
   Dim strAlbomPrimer As String
   Dim objRec As New ADODB.Recordset
   
   On Error GoTo HasError
   
   index = ComboBoxSer.ListIndex
   If index = -1 Then
      MsgBox "Не выбрана серия!", vbCritical, pcsVBProjectName
      Exit Sub
   End If
   'подтверждение
   If MsgBox("Добавить альбом узлов в серию - " & ComboBoxSer, vbQuestion + vbYesNo, pcsVBProjectName) = vbNo Then
      Exit Sub
   End If
   
   'очищаем листбокс
   ListBoxDetails.Clear
   ListBoxNodes.Clear
   'очищаем поля
   TextBoxKol = ""
   TextBoxMassa = ""
   TextBoxNaimen = ""
   TextBoxObozn = ""
   TextBoxNode = ""
   
   'закрываем Рекордсет
   If objRec.State = adStateOpen Then
      objRec.Close
   End If
                     
   FormRename.Caption = "Новый альбом"
   If ListBoxAlboms.ListIndex <> -1 Then
      strAlbomPrimer = ListBoxAlboms.Text
   End If
   If ComboBoxSer = "Типовые" Then
      If strAlbomPrimer = "" Then
         strAlbomPrimer = "90,ч.10,р.10.7-7"
      End If
      FormRename.TextBoxName = strAlbomPrimer
   Else
      If strAlbomPrimer = "" Then
         strAlbomPrimer = "1111-1-АС.У"
      End If
      FormRename.TextBoxName = strAlbomPrimer
   End If
   
   FormRename.Show
   'если нажали выход в форме FormRename
   If bolYes = False Then Exit Sub
   
   'запрос таблицы Альбомов
   strSql = "SELECT * FROM Альбомы;"
   objRec.Open Source:=strSql, ActiveConnection:=objConect, _
                  CursorType:=adOpenKeyset, LockType:=adLockOptimistic, Options:=adCmdText
   'добавляем новый альбом
   objRec.AddNew
   objRec!Obozn = FormRename.TextBoxName
   objRec!Ser_ID = ComboBoxSer.List(index, 1)
   objRec!Примечание = FormRename.TextBoxPrimech
   objRec.Update
   
   ListBoxAlboms.AddItem objRec!Obozn, 0
   ListBoxAlboms.List(0, 1) = objRec!Примечание

Exit Sub
   
HasError:
   Select Case Err.Number
      Case Else
         MsgBox Err.Description, vbCritical, pcsVBProjectName
   End Select
   
End Sub

Private Sub cmbAlbomDel_Click()
   
   Dim strSql As String
   Dim index As Integer
   Dim objRecSet2 As New ADODB.Recordset
   
   On Error GoTo HasError
   
   If ComboBoxSer.ListIndex = -1 Then
      MsgBox "Не выбрана серия!", vbCritical, pcsVBProjectName
      Exit Sub
   End If
   
   index = ListBoxAlboms.ListIndex
   
   If index = -1 Then
      Exit Sub
   End If

   'подтверждение
   If MsgBox("Удалить альбом узлов " & ListBoxAlboms & " из серии " & ComboBoxSer & "?", vbQuestion + vbYesNo, pcsVBProjectName) = vbNo Then
      Exit Sub
   End If
   
   'очищаем листбокс
   ListBoxDetails.Clear
   ListBoxNodes.Clear
   'очищаем поля
   TextBoxKol = ""
   TextBoxMassa = ""
   TextBoxNaimen = ""
   TextBoxObozn = ""
   TextBoxNode = ""
   
   'закрываем Рекордсет
   If objRecSet.State = adStateOpen Then
      objRecSet.Close
   End If
   
   'запрос таблицы Альбомов
   strSql = "SELECT * FROM Альбомы WHERE Obozn = '" & ListBoxAlboms & "';"
   objRecSet.Open Source:=strSql, ActiveConnection:=objConect, _
                  CursorType:=adOpenKeyset, LockType:=adLockOptimistic, Options:=adCmdText
   'находим запись альбома
   If objRecSet.EOF And objRecSet.BOF Then
      MsgBox "Альбом не найден в базе!", vbCritical, pcsVBProjectName
      Exit Sub
   End If
   
   'Найти детали по этому альбому, если они есть, то нельзя удалять альбом.
   '? нужно ли удалять детали этого альбома ? ХЗ, пока пускай остаются, авось пригодятся.
   strSql = "SELECT * FROM Изделия WHERE Obozn = '" & ListBoxAlboms & "' ORDER BY Name;"
   objRecSet2.Open Source:=strSql, ActiveConnection:=objConect, _
                  CursorType:=adOpenKeyset, LockType:=adLockOptimistic, Options:=adCmdText
   If objRecSet2.EOF = False Or objRecSet2.BOF = False Then
      MsgBox "Альбом нельзя удалять, т.к. есть детали с этим обозначением.", vbExclamation, pcsVBProjectName
      Exit Sub
   End If
   
   objRecSet.Delete
   objRecSet.Update
   
   '? нужно ли удалять детали этого альбома ? ХЗ, пока пускай остаются, авось пригодятся.
   
   ListBoxAlboms.RemoveItem index
   
Exit Sub
HasError:
   MsgBox Err.Description, vbCritical, pcsVBProjectName
   
End Sub

Private Sub cmbAlbomRename_Click()
   'переименовать альбом
   Dim strSql As String
   Dim strAlbom As String
   Dim strPrimech As String
   Dim index As String
   
   On Error GoTo HasError
   
   index = ListBoxAlboms.ListIndex
   If index = -1 Then
      MsgBox "Не выбран альбом!", vbCritical, pcsVBProjectName
      Exit Sub
   End If
   strAlbom = ListBoxAlboms
   strPrimech = ListBoxAlboms.List(index, 1)
   
   FormRename.Caption = "Переименовать альбом"
   FormRename.TextBoxName = ListBoxAlboms
   FormRename.TextBoxPrimech = strPrimech
   FormRename.Show
   'если нажали выход в форме FormRename
   If bolYes = False Then Exit Sub
   
   If strAlbom = FormRename.TextBoxName And strPrimech = FormRename.TextBoxPrimech Then
      'название не изменилось
      Exit Sub
   End If
   
   'очищаем листбокс
   ListBoxDetails.Clear
   ListBoxNodes.Clear
   'очищаем поля
   TextBoxKol = ""
   TextBoxMassa = ""
   TextBoxNaimen = ""
   TextBoxObozn = ""
   TextBoxNode = ""

   'записываем в базе изменение
   'запись в рекордсет альбомов
   If objRecSet.State = adStateOpen Then objRecSet.Close
   strSql = "SELECT * FROM Альбомы WHERE Obozn = '" & strAlbom & "';"
   objRecSet.Open Source:=strSql, ActiveConnection:=objConect, _
                  CursorType:=adOpenKeyset, LockType:=adLockOptimistic, Options:=adCmdText
   If objRecSet.EOF And objRecSet.BOF Then
      MsgBox "Альбом не найден в базе!", vbCritical, pcsVBProjectName
      Exit Sub
   End If
   objRecSet!Obozn = FormRename.TextBoxName
   objRecSet!Примечание = FormRename.TextBoxPrimech
   objRecSet.Update
   
   ListBoxAlboms.List(index, 0) = FormRename.TextBoxName
   ListBoxAlboms.List(index, 1) = FormRename.TextBoxPrimech
   
Exit Sub

HasError:
   Select Case Err.Number
      Case Else
         MsgBox Err.Description, vbCritical, pcsVBProjectName
   End Select

End Sub

Private Sub cmbBaseDetails_Click()
   'переход в редактор базы изделий
   
   Dim Node_index As Integer
   
   FormDetails.cmbOK.Visible = False
   FormDetails.cmbExit.Caption = "Закрыть"
   FormDetails.Caption = "Каталог деталей"
   FormDetails.Show
   
   'выделяем узел, при этом срабатывает опреация ListBoxNodes_click
   If ListBoxDetails.ListIndex <> -1 Then
      ListBoxDetails_Click
   End If
   
End Sub

Private Sub cmbBornPrim_Click()
   'назначаем место рождение узлу
   
   If ListBoxNodes.ListIndex = -1 Then
      'не выбран узел
      MsgBox "Не выбран узел!", vbCritical, pcsVBProjectName
      Exit Sub
   End If
   
   objRecNodes.UpdateBatch
   
End Sub

Private Sub cmbCancel_Click()
   On Error Resume Next
   objRecNodesDetail.Cancel
   objRecNodes.Cancel
End Sub

Private Sub cmbDetPrimech_Click()
   'изменить/добавить примечание детале
   
   Dim strSql As String
   Dim objRecSetTemp As New ADODB.Recordset
   Dim index As Integer
   Dim indexNode As Integer
   Dim strPrimech As String
   
   On Error GoTo HasError
   
   indexNode = ListBoxNodes.ListIndex
   index = ListBoxDetails.ListIndex
   If index = -1 Then
      'не выбрана деталь
      MsgBox "Не выбрана деталь!", vbCritical, pcsVBProjectName
      Exit Sub
   End If
   
   'запрос состава узла
   If ComboBoxSer.Text = "Типовые" Then
      strSql = "SELECT * FROM Типовые_состав WHERE Node_ID = " & ListBoxNodes.List(indexNode, 1) & " AND Detail_ID = " & ListBoxDetails.List(index, 1)
   Else
      strSql = "SELECT * FROM Состав WHERE Node_ID = " & ListBoxNodes.List(indexNode, 1) & " AND Detail_ID = " & ListBoxDetails.List(index, 1)
   End If
   objRecSetTemp.Open Source:=strSql, ActiveConnection:=objConect, _
            CursorType:=adOpenKeyset, LockType:=adLockOptimistic, Options:=adCmdText
   If objRecSetTemp.EOF And objRecSetTemp.BOF Then
      MsgBox "Деталь не найдена!", vbCritical, pcsVBProjectName
      Exit Sub
   End If
   
   strPrimech = ListBoxDetails.List(index, 3)
   FormRename.Caption = "Примечание к детале " & ListBoxDetails
   FormRename.Label1.Visible = False
   FormRename.Label2.Visible = False
   FormRename.TextBoxName.Visible = False
   FormRename.TextBoxName = "False"
   FormRename.TextBoxPrimech = strPrimech
   FormRename.Show
   'если нажали выход
   If bolYes = False Then Exit Sub
   'если примечание не изменилось
   If strPrimech = FormRename.TextBoxPrimech Then Exit Sub
   
   objRecSetTemp!Примечание = FormRename.TextBoxPrimech
   objRecSetTemp.Update
   
   ListBoxDetails.List(index, 3) = FormRename.TextBoxPrimech
   
   LabelPrimech = FormRename.TextBoxPrimech
   
   FormRename.Label1.Visible = True
   FormRename.Label2.Visible = True
   FormRename.TextBoxName.Visible = True
   FormRename.TextBoxName = ""
   
Exit Sub
HasError:
   MsgBox Err.Description, vbCritical, pcsVBProjectName
   
End Sub

Private Sub cmbInsertNode_Click()
   'вставка блока узла в текущий чертеж
   
   Dim strNodeDWGFullPath As String
   Dim objBlNode As AcadBlockReference
   Dim varPt As Variant
   Dim varAtr As Variant
   Dim objAtr As AcadAttributeReference
   
   On Error GoTo HasError

   If ListBoxNodes.ListIndex = -1 Then
      MsgBox "Не выбран узел!", vbCritical, pcsVBProjectName
      Exit Sub
   End If
   
   If ListBoxDetails.ListCount = 0 Then
      MsgBox "В узле нет деталей!", vbCritical, pcsVBProjectName
      Exit Sub
   End If
   
   'проверяем масштаб на соответствие числу doubles
   If Not IsNumeric(TextBoxM) Then
      MsgBox "Масштаб не верный. Должно быть число!", vbCritical, pcsVBProjectName
      Exit Sub
   End If
   
   strNodeDWGFullPath = Funcions.GetMacroFolder(pcsVBProjectName) & "\Блоки\Узел.dwg"
   
   'скрываем окно
   Hide
   
   ThisDrawing.ActiveLayer.LayerOn = True
   ThisDrawing.ActiveLayer.Lock = False
   
   varPt = ThisDrawing.Utility.GetPoint(, "Точка вставки")
   Set objBlNode = ThisDrawing.ModelSpace.InsertBlock(varPt, strNodeDWGFullPath, TextBoxM, TextBoxM, 1, 0)
   
   'назначаем значение атрибуту
   For Each varAtr In objBlNode.GetAttributes
      Set objAtr = varAtr
      If LCase(objAtr.TagString) = "марка" Then
         objAtr.TextString = ListBoxNodes.Text
      ElseIf LCase(objAtr.TagString) = "обозначение" Then
         objAtr.TextString = ListBoxAlboms
      End If
   Next
   
   FormNodes.Show
   
Exit Sub
HasError:
   MsgBox Err.Description, vbCritical, pcsVBProjectName
   
End Sub

Private Sub cmbNodeRename_Click()
   'переименовать выделенный узел
   
   Dim strNode As String
   Dim strPrimech As String
   Dim strSql As String
   Dim index As Integer
   
   On Error GoTo HasError
   
   index = ListBoxNodes.ListIndex
   If index = -1 Then
      MsgBox "Нужно выбрать узел для его удаления!", vbCritical, pcsVBProjectName
      Exit Sub
   End If
   
   strNode = ListBoxNodes
   strPrimech = ListBoxNodes.List(index, 2)
      
   'запрос узла из таблицы Крон_узлы
   If objRecSet.State = adStateOpen Then objRecSet.Close
   If ComboBoxSer.Text = "Типовые" Then
      strSql = "SELECT * FROM Типовые_Узлы WHERE ID = " & ListBoxNodes.List(index, 1)
   Else
      strSql = "SELECT * FROM Узлы WHERE ID = " & ListBoxNodes.List(index, 1)
   End If
   objRecSet.Open Source:=strSql, ActiveConnection:=objConect, _
                  CursorType:=adOpenKeyset, LockType:=adLockOptimistic, Options:=adCmdText
   If objRecSet.EOF And objRecSet.BOF Then
      MsgBox "Узел не найден!", vbCritical, pcsVBProjectName
      Exit Sub
   End If
   
   'форма переименования
   FormRename.Caption = "Переименование узла"
   FormRename.TextBoxName = strNode
   FormRename.Label2 = "Старое имя = " & strNode
   FormRename.TextBoxPrimech = strPrimech
   FormRename.Show
   'если нажали выход в форме FormRename
   If bolYes = False Then Exit Sub
   If FormRename.TextBoxName = strNode And strPrimech = FormRename.TextBoxPrimech Then Exit Sub
   
   'переименовать узел
   objRecSet!Name = FormRename.TextBoxName
   objRecSet!Примечание = FormRename.TextBoxPrimech
   objRecSet.Update
   
   ListBoxNodes.List(index, 0) = objRecSet!Name
   ListBoxNodes.List(index, 2) = FormRename.TextBoxPrimech

Exit Sub

HasError:
   Select Case Err.Number
      Case Else
         MsgBox Err.Description, vbCritical, pcsVBProjectName
   End Select
   
End Sub

Private Sub cmbSave_Click()
   
   objRecNodesDetail.UpdateBatch
   objRecNodes.UpdateBatch
   
End Sub

Private Sub cmbExit_Click()
   If objConect.State = adStateOpen Then objConect.Close
   Hide
End Sub

Private Sub cmbNodeAdd_Click()
   'создание нового узла
   
   Dim i As Integer
   Dim strNodeName As String
   Dim strSql As String
   Dim objRec As New ADODB.Recordset
   
   On Error GoTo HasError
   
   If ListBoxAlboms.ListIndex = -1 Then
      MsgBox "Не выбран альбом!", vbCritical, pcsVBProjectName
      Exit Sub
   End If
   
   'форма для имени узла
   FormRename.Caption = "Имя для нового узла"
   FormRename.Label2 = "(в русской раскладке)"
   FormRename.TextBoxPrimech = ""
   If ListBoxNodes.ListIndex <> -1 Then
      FormRename.TextBoxName = ListBoxNodes
   End If
   FormRename.Show
   'если нажали выход в форме FormRename
   If bolYes = False Then Exit Sub
   
   strNodeName = FormRename.TextBoxName
   
   'запрос узлов текущей серии из таблицы Крон_узлы
   If objRec.State = adStateOpen Then objRec.Close
   If ComboBoxSer.Text = "Типовые" Then
      strSql = "SELECT * FROM Типовые_узлы WHERE Obozn = '" & ListBoxAlboms & "';"
   Else
      strSql = "SELECT * FROM Узлы  WHERE Obozn = '" & ListBoxAlboms & "';"
   End If
   objRec.Open Source:=strSql, ActiveConnection:=objConect, _
                  CursorType:=adOpenKeyset, LockType:=adLockOptimistic, Options:=adCmdText
   
   'добавляем запись в RecSet
   
   objRec.AddNew
   objRec!Name = strNodeName
   objRec!Obozn = ListBoxAlboms
   If ComboBoxSer.Text <> "Типовые" Then
    objRec!SerID = ComboBoxSer.List(ComboBoxSer.ListIndex, 1)
   End If
   objRec!Примечание = FormRename.TextBoxPrimech
   objRec.Update
   
   'добавляем запись в листбокс узлов
   ListBoxNodes.AddItem strNodeName, 0
   ListBoxNodes.Column(1, 0) = objRec!ID
   ListBoxNodes.Column(2, 0) = objRec!Примечание
   
   'выделяем добавленный узел
   ListBoxNodes.Selected(0) = True
   
Exit Sub
   
HasError:
   Select Case Err.Number
      Case Else
         MsgBox Err.Description, vbCritical, pcsVBProjectName
   End Select
   
End Sub

Private Sub cmbPrimKolDet_Click()
   'записываем кол-во деталей в RecSet
   
   Dim strSql As String
   Dim objRecSetTemp As New ADODB.Recordset
   Dim Det_index As Integer
   Dim Node_index As Integer
   Dim intKol As Integer
   
   On Error GoTo HasError
   
   Node_index = ListBoxNodes.ListIndex
   Det_index = ListBoxDetails.ListIndex
   If Det_index = -1 Then
      'не выбран узел
      MsgBox "Не выбрана деталь!", vbCritical, pcsVBProjectName
      Exit Sub
   End If
   
   intKol = TextBoxKol
      
   'запрос детали из таблицы состава узлов по ее ID
   If ComboBoxSer.Text = "Типовые" Then
      strSql = "SELECT Node_ID, Detail_ID, Range FROM Типовые_состав WHERE Detail_ID = " & ListBoxDetails.Column(1, Det_index) & " AND Node_ID = " & ListBoxNodes.List(Node_index, 1)
   Else
      strSql = "SELECT Node_ID, Detail_ID, Range FROM Состав WHERE Detail_ID = " & ListBoxDetails.Column(1, Det_index) & " AND Node_ID = " & ListBoxNodes.List(Node_index, 1)
   End If
   objRecSetTemp.Open Source:=strSql, ActiveConnection:=objConect, _
            CursorType:=adOpenKeyset, LockType:=adLockOptimistic, Options:=adCmdText
   objRecSetTemp!Range = TextBoxKol
   objRecSetTemp.Update
   'изменяем кол-во в листбоксе 2 колонка
   ListBoxDetails.Column(2, Det_index) = TextBoxKol

Exit Sub

HasError:
   Select Case Err.Number
      Case 13 '"Type mismatch" не совпадение типа, в intKol
         MsgBox "Нужно ввести число!", vbCritical, pcsVBProjectName
      Case Else
         MsgBox Err.Description, vbCritical, pcsVBProjectName
   End Select
   
End Sub

Private Sub cmbSearch_Click()
   'выводим список найденных узлов
   
   Dim RecSetSearch As ADODB.Recordset
   RecSetSearch.Open Source:="Select Name From Nodes Where Name like " & "'*" & TextBoxSearchNode & "*';", ActiveConnection:=objConect, _
                  CursorType:=adOpenStatic, LockType:=adLockReadOnly, Options:=adCmdText
   If objRecSet.EOF And objRecSet.BOF Then
      'ничего не найдено
      Exit Sub
   End If
   
   RecSetSearch.Save "D:\Vildar\Граждан\Макросы\BaseNodes\Search.xml", adPersistXML
   
End Sub

Private Sub cmbNodeDel_Click()
   
   Dim strNode As String
   Dim strSql As String
   Dim strConect As String
   Dim index As Integer
   
   On Error GoTo HasError
   
   index = ListBoxNodes.ListIndex
   If index = -1 Then
      MsgBox "Нужно выбрать узел для его удаления!", vbCritical, pcsVBProjectName
      Exit Sub
   End If
   
   strNode = ListBoxNodes
   
   'запрос на подтверждение удаления
   If MsgBox("Удалить узел " & strNode, vbYesNo + vbQuestion, pcsVBProjectName) = vbNo Then 'нет
      Exit Sub
   End If
   
   'запрос узла из таблицы Крон_узлы
   If objRecSet.State = adStateOpen Then objRecSet.Close
   If ComboBoxSer.Text = "Типовые" Then
      strSql = "SELECT * FROM Типовые_Узлы WHERE ID = " & ListBoxNodes.List(index, 1)
   Else
      strSql = "SELECT * FROM Узлы WHERE ID = " & ListBoxNodes.List(index, 1)
   End If
   objRecSet.Open Source:=strSql, ActiveConnection:=objConect, _
                  CursorType:=adOpenKeyset, LockType:=adLockOptimistic, Options:=adCmdText
   If objRecSet.EOF And objRecSet.BOF Then
      MsgBox "Узел не найден!", vbCritical, pcsVBProjectName
      Exit Sub
   End If
   
   'удаляем узел
   objRecSet.Delete
   'обновление после нажатия сохранить, или отменить изм
   objRecSet.Update
   
   ListBoxNodes.RemoveItem index
   
Exit Sub
HasError:
   MsgBox Err.Description, vbCritical, pcsVBProjectName
      
End Sub

Private Sub cmbDetailAdd_Click()
   'добавление изделия из таблицы изделий
   'причем в типовую серию нельзя добавить деталь с типом = любой серии кроме типовые
   'а в не типовую серию нельзя добавить деталь из другой серии
   
   Dim strSql As String
   Dim i As Integer
   Dim objRecTemp As New ADODB.Recordset
   Dim objRec As New ADODB.Recordset
   Dim indexLbNodes As Integer
   Dim indexLbDetails As Integer
   
   On Error GoTo HasError
   
   indexLbNodes = ListBoxNodes.ListIndex
   If indexLbNodes = -1 Then
      MsgBox "Не выбран узел!", vbCritical, pcsVBProjectName
      Exit Sub
   End If
   
   bolYes = False
   FormDetails.cmbExit.Caption = "Отмена"
   FormDetails.cmbOK.Visible = True
   FormDetails.Caption = "Добавление детали в узел " & ListBoxNodes.Text
   FormDetails.Show
   If bolYes = False Then
      'нажали отмену в форме FormDetails
      Exit Sub
   End If
   'выбранная строчка в форме FormDetails для добавление в узел
   'Set objListItem = FormDetails.ListViewTablDetails.SelectedItem
   indexLbDetails = FormDetails.ListBoxTableDetails.ListIndex
   If indexLbDetails = -1 Then 'objListItem Is Nothing Then
      'не выбрана деталь
      MsgBox "Небыло выбрано изделие для добавления", vbExclamation, pcsVBProjectName
      Exit Sub
   End If
   
   'что за серия куда добавляется деталь
   If ComboBoxSer = "Типовые" Then
      'в типовой узел нельзя добавить деталь из наших серий
      For i = 0 To ComboBoxSer.ListCount - 1
         If ComboBoxSer.List(i) <> "Типовые" Then
            If FormDetails.ListBoxTableDetails.List(indexLbDetails, 4) = ComboBoxSer.List(i) Then
               MsgBox "В типовой узел нельзя добавить деталь из наших серий!", vbCritical, pcsVBProjectName
               Exit Sub
            End If
         End If
      Next
   Else
      'значит одна из наших
      'нельзя добавить деталдь из другой серии
      For i = 0 To ComboBoxSer.ListCount - 1
         If ComboBoxSer.List(i) <> "Типовые" And ComboBoxSer.List(i) <> ComboBoxSer.Text Then
            If FormDetails.ListBoxTableDetails.List(indexLbDetails, 4) = ComboBoxSer.List(i) Then
               MsgBox "В узел нельзя добавить деталь из другой серии!", vbCritical, pcsVBProjectName
               Exit Sub
            End If
         End If
      Next
   End If
   
   'запрос состава узла
   'закрываем Рекордсет
   If objRec.State = adStateOpen Then objRec.Close
   If ComboBoxSer.Text = "Типовые" Then
      strSql = "SELECT * FROM Типовые_состав WHERE Типовые_состав.Node_ID = " & ListBoxNodes.List(indexLbNodes, 1) & ";"
   Else
      strSql = "SELECT * FROM Состав WHERE Состав.Node_ID = " & ListBoxNodes.List(indexLbNodes, 1) & ";"
   End If
   objRec.Open Source:=strSql, ActiveConnection:=objConect, _
                  CursorType:=adOpenKeyset, LockType:=adLockOptimistic, Options:=adCmdText
   
   'добавляем запись в RecSet
   objRec.AddNew
   objRec!Detail_ID = FormDetails.ListBoxTableDetails.List(indexLbDetails, 5) ' objListItem.ListSubItems.Item(5).Text
   objRec!Node_ID = ListBoxNodes.List(indexLbNodes, 1)
   objRec!Range = 1
   objRec.Update
   
   'добавляем деталь в данные по узлу
   ListBoxDetails.AddItem FormDetails.ListBoxTableDetails.List(indexLbDetails, 0), 0 'objListItem.Text, 0
   ListBoxDetails.Column(1, 0) = FormDetails.ListBoxTableDetails.List(indexLbDetails, 5) 'objListItem.ListSubItems.Item(5).Text 'ID
   ListBoxDetails.Column(2, 0) = 1 'кол-во деталей
   ListBoxDetails.Column(3, 0) = ""
   TextBoxKol = 1
   TextBoxMassa = FormDetails.ListBoxTableDetails.List(indexLbDetails, 2) 'objListItem.ListSubItems.Item(2).Text
   TextBoxNaimen = FormDetails.ListBoxTableDetails.List(indexLbDetails, 3) 'objListItem.ListSubItems.Item(3).Text
   TextBoxObozn = FormDetails.ListBoxTableDetails.List(indexLbDetails, 1) ' objListItem.ListSubItems.Item(1).Text
   
Exit Sub

HasError:
   Select Case Err.Number
      Case Else
         MsgBox Err.Description, vbCritical, pcsVBProjectName
   End Select

End Sub

Private Sub cmbSearchNode_Click()
   'поиск узла по марке
   FormSearchNode.Show
End Sub

Private Sub cmbSerAdd_Click()
   'создание новой серии
   
   Dim strName As String
   Dim strSql As String
   Dim strMacroFolder As String
   Dim recNewSer As New ADODB.Recordset
'   Dim objConnect As New Connection
   Dim objCatalog As New ADOX.Catalog
   Dim objTable As ADOX.Table
   Dim objColumn As ADOX.Column
   Dim objKey As ADOX.key
   Dim objIndex As ADOX.index
   
   On Error GoTo HasError
   
'   objCatalog.ActiveConnection = objConect
'   Set objTable = objCatalog.Tables("Изделия")
'   Dim objCom As New ADODB.Command
''   strSQL = "create table tree (set_id integer primary key, fk_parent text, ОписаниеЗаказа NCHAR VARYING (255),  " & _
''      "constraint parent_fkey foreign key (ID) references Таблица1 on update cascade on delete cascade);"
'   strSQL = "create table tree (set_id int primary key, fk_parent text, ОписаниеЗаказа text);"
'   objCom.ActiveConnection = objConect
'   objCom.CommandType = adCmdText
'   objCom.CommandText = strSQL
'   objCom.Execute
   
   'запрос имени серии
   FormRename.Caption = "Новая серия"
   FormRename.Label2 = ""
   FormRename.Show
   'если нажали выход в форме FormRename
   If bolYes = False Then Exit Sub
   
   'имя без пробелов по краям
   strName = VBA.Trim(FormRename.TextBoxName)
   
   'запрос серии из таблицы Серии
   strSql = "SELECT * FROM Серии"
   recNewSer.Open Source:=strSql, ActiveConnection:=objConect, _
         CursorType:=adOpenKeyset, LockType:=adLockOptimistic, Options:=adCmdText
   'добавляем запись
   recNewSer.AddNew
   recNewSer!Ser = strName
   recNewSer!Примечание = FormRename.TextBoxPrimech
   recNewSer.Update
   
'   'нужно создать две таблицы, ИмяСерии_Узлы и ИмяСерии_состав
'   strMacroFolder = Funcions.GetMacroFolder(pcsVBProjectName)
'   'открытие базы
'   objConnect.ConnectionString = "Provider=Microsoft.Jet.OLEDB.4.0;Data Source= " & strMacroFolder & "\dbNodes.mdb"
'   objConnect.CursorLocation = adUseClient
'   objConnect.Mode = adModeWrite
'   objConnect.Open

'   'подключение к базе
'   objCatalog.ActiveConnection = objConect
''   objCatalog.ActiveConnection = strProvider & "Data Source=" & strMacroFolder & "\dbNodes.mdb"
'
'   'создаем вторую таблицу Состава
'   Set objTable = New ADOX.Table
'   objTable.Name = strName & "_состав"
'   objTable.ParentCatalog = objCatalog
'   'создаем поле Node_ID
'   Set objColumn = New ADOX.Column
'   objColumn.ParentCatalog = objCatalog
'   objColumn.Name = "Node_ID"
'   objColumn.Type = adInteger
'   objTable.Columns.Append objColumn
'   'создаем поле Obozn_ID
'   Set objColumn = New ADOX.Column
'   objColumn.Name = "Detail_ID"
'   objColumn.Type = adInteger
'   objColumn.ParentCatalog = objCatalog
'   objTable.Columns.Append objColumn
'   'остальные поля
'   objTable.Columns.Append "Range", adSmallInt
'   objTable.Columns.Append "Примечание", adVarWChar, 255
'   objTable.Columns("Примечание").Properties("Default") = ""
'   'задаем ключи
'   Set objKey = New ADOX.key
'   objKey.Name = "Составной"
'   objKey.Columns.Append "Node_ID"
'   objKey.Columns.Append "Detail_ID"
'   objKey.Type = adKeyPrimary
'   objKey.UpdateRule = adRICascade
'   objKey.DeleteRule = adRICascade
'   'добавляем ключ в таблицу Node_ID
'   objTable.Keys.Append objKey
'   'задаем связь Сер_состав.Detail_ID = Изделия.ID
'   Set objKey = New ADOX.key
'   objKey.Name = "Связь_" & strName
'   objKey.Type = adKeyForeign
'   objKey.UpdateRule = adRICascade
'   objKey.DeleteRule = adRICascade
'   objKey.RelatedTable = "Изделия"
'   Set objColumn = New ADOX.Column
'   objColumn.Name = "Detail_ID"
'   objColumn.RelatedColumn = "ID"
'   objKey.Columns.Append objColumn
'   objTable.Keys.Append objKey
'   'добавляем таблицу в базу dbNodes
'   objCatalog.Tables.Append objTable
'
'   'создаем таблицу ИмяСерии_узлы
'   Set objTable = New ADOX.Table
'   objTable.Name = strName & "_узлы"
'   objTable.ParentCatalog = objCatalog
'   'создаем поле счетчика
'   Set objColumn = New ADOX.Column
'   objColumn.Name = "ID"
'   objColumn.Type = adInteger
'   Set objColumn.ParentCatalog = objCatalog
'   objColumn.Properties("AutoIncrement") = True
'   objColumn.Properties("Seed") = CLng(1)
'   objColumn.Properties("Increment") = CLng(1)
'   objTable.Columns.Append objColumn
'   'остальные поля
'   objTable.Columns.Append "Name", adVarWChar, 50
'   objTable.Columns.Append "Obozn", adVarWChar, 50
'   objTable.Columns.Append "Примечание", adVarWChar, 255
'   objTable.Columns("Примечание").Properties("Default") = ""
'   'задаем ключ Name+Obozn
'   Set objKey = New ADOX.key
'   objKey.Name = "Составной"
'   objKey.Columns.Append "Name"
'   objKey.Columns.Append "Obozn"
'   objKey.Type = adKeyPrimary
'   'добавляем ключ в таблицу
'   objTable.Keys.Append objKey
'   'задаем ключ ID
'   Set objKey = New ADOX.key
'   objKey.Name = "ID"
'   objKey.Columns.Append "ID"
'   objKey.Type = adKeyUnique
'   'добавляем ключ в таблицу
'   objTable.Keys.Append objKey
'   'задаем связь Альбомы.Obozn = Имя_узлы.Obozn
'   Set objKey = New ADOX.key
'   objKey.Name = "Связь_альбом_" & strName
'   objKey.Type = adKeyForeign
'   objKey.UpdateRule = adRICascade
'   objKey.DeleteRule = adRICascade
'   objKey.RelatedTable = "Альбомы"
'   Set objColumn = New ADOX.Column
'   objColumn.Name = "Obozn"
'   objColumn.RelatedColumn = "Obozn"
'   objKey.Columns.Append objColumn
'   objTable.Keys.Append objKey
'   'добавляем таблицу в базу dbNodes
'   objCatalog.Tables.Append objTable
'   'задаем связь Сер_узлы.ID=Сер_состав.Node_ID
'   Set objTable = objCatalog.Tables(strName & "_состав")
'   Set objKey = New ADOX.key
'   objKey.Name = "Связь_узел_" & strName
'   objKey.Type = adKeyForeign
'   objKey.UpdateRule = adRICascade
'   objKey.DeleteRule = adRICascade
'   objKey.RelatedTable = strName & "_узлы"
'   Set objColumn = New ADOX.Column
'   objColumn.Name = "Node_ID"
'   objColumn.RelatedColumn = "ID"
'   objKey.Columns.Append objColumn
'   'добавляем ключ в таблицу Detail_ID
'   objTable.Keys.Append objKey
   
   ComboBoxSer.AddItem strName, 0
   ComboBoxSer.List(0, 1) = recNewSer!ID
   ComboBoxSer.List(0, 2) = recNewSer!Примечание
   
   ComboBoxSer = strName
   
Exit Sub
   
HasError:
   Select Case Err.Number
      Case Else
         MsgBox Err.Description, vbCritical, pcsVBProjectName
   End Select
         
End Sub

Private Sub cmbSerDel_Click()
   'удаление серии
   
   Dim objCommand As New ADODB.Command
   Dim objRec As New ADODB.Recordset
   Dim strSql As String
   Dim strMacroFolder As String
   Dim strBDTempPath As String
   Dim index As Integer
'   Dim objFS As New FileSystemObject
   Dim objFS As Object
   
   On Error GoTo HasError
   
   index = ComboBoxSer.ListIndex
   If index = -1 Then
      MsgBox "Не выбрана серия", vbCritical, pcsVBProjectName
   End If
   
   If ComboBoxSer = "Типовые" Then
      MsgBox "Типовую серию нельзя удалить!", vbCritical, pcsVBProjectName
      Exit Sub
   End If
   
   'подтверждение удаления
   If MsgBox("Удалить серию - " & ComboBoxSer, vbQuestion + vbYesNo, pcsVBProjectName) = vbNo Then Exit Sub
   
   'создаем копию базы, в [макрос]\Temp\dbNodes_temp.mdb
   strMacroFolder = Funcions.GetMacroFolder(pcsVBProjectName)
   strBDTempPath = strMacroFolder & "\Temp"
   If Dir(strBDTempPath, vbDirectory) = "" Then
      MkDir strBDTempPath
   End If
   Set objFS = CreateObject("Scripting.FileSystemObject")
   objFS.CopyFile strMacroFolder & "\Базы\dbNodes.mdb", strBDTempPath & "\dbNodes_temp.mdb"
   
   'запрос серии из таблицы Серии
   strSql = "SELECT * FROM Серии WHERE Ser = '" & ComboBoxSer & "'"
   objRec.Open Source:=strSql, ActiveConnection:=objConect, _
            CursorType:=adOpenKeyset, LockType:=adLockOptimistic, Options:=adCmdText
   If objRec.EOF And objRec.BOF Then
      MsgBox "Серия не найдена в базе!", vbCritical, pcsVBProjectName
      Exit Sub
   End If
   'удаляем запись
   objRec.Delete
   
'   'удаление таблиц
'   objCommand.ActiveConnection = objConect
'   objCommand.CommandType = adCmdText
'   'удаляем связь Альбом - узлы
'   objCommand.CommandText = "ALTER TABLE [" & ComboBoxSer & "_узлы] DROP CONSTRAINT [Связь_альбом_" & ComboBoxSer & "]"
'   objCommand.Execute
'   'удаляем связь узлы - состав
'   objCommand.CommandText = "ALTER TABLE [" & ComboBoxSer & "_состав] DROP CONSTRAINT [Связь_узел_" & ComboBoxSer & "]"
'   objCommand.Execute
'   'удаляем связь состав - изделия
'   objCommand.CommandText = "ALTER TABLE [" & ComboBoxSer & "_состав] DROP CONSTRAINT [Связь_" & ComboBoxSer & "]"
'   objCommand.Execute
'   'удаляем таблицу узлов
'   objCommand.CommandText = "DROP TABLE [" & ComboBoxSer & "_узлы]"
'   objCommand.Execute
'   'удаляем таблицу состава
'   objCommand.CommandText = "DROP TABLE [" & ComboBoxSer & "_состав]"
'   objCommand.Execute
   
   'удаление всез деталей этой серии
   objCommand.ActiveConnection = objConect
   objCommand.CommandText = "DELETE * FROM Изделия WHERE Type = '" & ComboBoxSer & "'"
   objCommand.Execute
   
   ComboBoxSer.RemoveItem index
   
Exit Sub

HasError:
   Select Case Err.Number
      Case Else
         MsgBox Err.Description & vbCrLf & "Рекомендуется восстановить базу из файла - " & strBDTempPath & "\dbNodes_temp.mdb", vbCritical, pcsVBProjectName
         'MsgBox "Рекомендуется восстановить базу из файла - " & strBDTempPath & "\dbNodes_temp.mdb", vbExclamation, pcsVBProjectName
   End Select
   
End Sub

Private Sub cmbSerRename_Click()
   'редактривование имени и примечания к серии
   
   Dim objRec As New ADODB.Recordset
   Dim strSql As String
   Dim index As Integer
   
   Dim objCatalog As New ADOX.Catalog
   Dim objTable As New ADOX.Table
   Dim objKey As New ADOX.key
   Dim objColumn As New ADOX.Column
   
   On Error GoTo HasError
   
   index = ComboBoxSer.ListIndex
   If index = -1 Then
      MsgBox "Не выбрана серия", vbCritical, pcsVBProjectName
   End If
   
   If ComboBoxSer = "Типовые" Then
      MsgBox "Имя типовой серии нельзя редактировать!", vbCritical, pcsVBProjectName
      Exit Sub
   End If
   
   'запрос серии из таблицы Серии
   strSql = "SELECT * FROM Серии WHERE Ser = '" & ComboBoxSer & "'"
   If objRec.State = adStateOpen Then objRec.Close
   objRec.Open Source:=strSql, ActiveConnection:=objConect, _
            CursorType:=adOpenKeyset, LockType:=adLockOptimistic, Options:=adCmdText
   If objRec.EOF And objRec.BOF Then
      MsgBox "Серия не найдена в базе!", vbCritical, pcsVBProjectName
      Exit Sub
   End If
   'выводим форму для внесения изменений
   FormRename.Caption = "Редактирование серии - " & ComboBoxSer
   FormRename.Label2.Visible = False
   FormRename.TextBoxName = objRec!Ser
   FormRename.TextBoxPrimech = objRec!Примечание
   FormRename.Show
   'если нажали отмену в форме
   If bolYes = False Then Exit Sub
   'если не изменилось имя серии и примечание
   If objRec!Ser = FormRename.TextBoxName And objRec!Примечание = FormRename.TextBoxPrimech Then Exit Sub
   
   'редактируем серию
   objRec!Ser = FormRename.TextBoxName
   objRec!Примечание = FormRename.TextBoxPrimech
   objRec.Update
   
'   'редактируем названия таблиц Узлов и Сосмтава
'   'подключение к базе через ADOX
'   objCatalog.ActiveConnection = objConect
'   'получаем таблу "ИмяСер_узлы"
'   Set objTable = objCatalog.Tables(ComboBoxSer & "_узлы")
'   objTable.Name = objRec!Ser & "_узлы"
'   'нужно отредактировать ключ "Связь_альбом_ИмяСер"
'   objTable.Keys.Delete ("Связь_альбом_" & ComboBoxSer)
'   Set objKey = New ADOX.key
'   objKey.Name = "Связь_альбом_" & objRec!Ser
'   objKey.Type = adKeyForeign
'   objKey.UpdateRule = adRICascade
'   objKey.DeleteRule = adRICascade
'   objKey.RelatedTable = "Альбомы"
'   Set objColumn = New ADOX.Column
'   objColumn.Name = "Obozn"
'   objColumn.RelatedColumn = "Obozn"
'   objKey.Columns.Append objColumn
'   objTable.Keys.Append objKey
'
'   'получаем таблу "ИмяСер_состав"
'   Set objTable = objCatalog.Tables(ComboBoxSer & "_состав")
'   objTable.Name = objRec!Ser & "_состав"
'   'нужно отредактировать ключ "Связь_узел_ИмяСер"
'   objTable.Keys.Delete ("Связь_узел_" & ComboBoxSer)
'   Set objKey = New ADOX.key
'   objKey.Name = "Связь_узел_" & objRec!Ser
'   objKey.Type = adKeyForeign
'   objKey.UpdateRule = adRICascade
'   objKey.DeleteRule = adRICascade
'   objKey.RelatedTable = objRec!Ser & "_узлы"
'   Set objColumn = New ADOX.Column
'   objColumn.Name = "Node_ID"
'   objColumn.RelatedColumn = "ID"
'   objKey.Columns.Append objColumn
'   'добавляем ключ в таблицу Detail_ID
'   objTable.Keys.Append objKey
   
   'редактируем запись в комбобоксе
   ComboBoxSer.List(index, 0) = objRec!Ser
   ComboBoxSer.List(index, 2) = objRec!Примечание
   
Exit Sub

HasError:
   Select Case Err.Number
      Case Else
         MsgBox Err.Description, vbCritical, pcsVBProjectName
   End Select
   
End Sub

Private Sub cmbSostavAlbom_Click()
   'построение спец-ии состава узлов выбранного альбома
   
   Dim strSql As String
   Dim objRecSetSostav As New ADODB.Recordset
   Dim colNodes As New Collection
   Dim objNode As clNode
   Dim objDetail As clDetail
   
   On Error GoTo HasError
     
   If ListBoxAlboms.ListIndex = -1 Then
      MsgBox "Не выбран альбом!", vbCritical, pcsVBProjectName
      Exit Sub
   End If
   
   'проверяем масштаб на соответствие числу doubles
   If Not IsNumeric(TextBoxM) Then
      MsgBox "Масштаб не верный. Должно быть число!", vbCritical, pcsVBProjectName
      Exit Sub
   End If
   
   'запрос узлов для указанного альбома(Obozn) из таблицы Серия_узлы
   If ComboBoxSer.Text = "Типовые" Then
      strSql = "SELECT Name, ID FROM Типовые_узлы WHERE Obozn='" & ListBoxAlboms & "'ORDER BY Name;"
   Else
      strSql = "SELECT Name, ID FROM Узлы WHERE Obozn='" & ListBoxAlboms & "'ORDER BY Name;"
   End If
   objRecSetSostav.Open Source:=strSql, ActiveConnection:=objConect, _
            CursorType:=adOpenKeyset, LockType:=adLockOptimistic, Options:=adCmdText
   If objRecSetSostav.EOF And objRecSetSostav.BOF Then
      MsgBox "Нет узлов в этом альбоме!", vbInformation, pcsVBProjectName
      Exit Sub
   End If
   'заполняем массив узлов
   objRecSetSostav.MoveFirst
   Do Until objRecSetSostav.EOF
      Set objNode = New clNode
      objNode.ID = objRecSetSostav!ID
      objNode.Name = objRecSetSostav!Name
      colNodes.Add objNode
      objRecSetSostav.MoveNext
   Loop
   
   'заполнение колекций деталей для всех узлов objNode.colDetails
   For Each objNode In colNodes
      objRecSetSostav.Close
      'запрос состава узла
      If ComboBoxSer.Text = "Типовые" Then
         strSql = "SELECT Типовые_состав.Range, Изделия.Name, Изделия.Massa, Изделия.Obozn, Изделия.Naimen " & _
                  "FROM Изделия INNER JOIN Состав ON Изделия.ID = Состав.Detail_ID " & _
                  "WHERE Типовые_состав.Node_ID = " & objNode.ID & " " & _
                  "ORDER BY Изделия.Name;"
      Else
         strSql = "SELECT Состав.Range, Изделия.Name, Изделия.Massa, Изделия.Obozn, Изделия.Naimen " & _
                  "FROM Изделия INNER JOIN Состав ON Изделия.ID = Состав.Detail_ID " & _
                  "WHERE Состав.Node_ID = " & objNode.ID & " " & _
                  "ORDER BY Изделия.Name;"
      End If
      objRecSetSostav.Open Source:=strSql, ActiveConnection:=objConect, _
               CursorType:=adOpenKeyset, LockType:=adLockOptimistic, Options:=adCmdText
      If objRecSetSostav.EOF And objRecSetSostav.BOF Then
         'нет деталей в узле
      Else
         objRecSetSostav.MoveFirst
         Do Until objRecSetSostav.EOF
            Set objDetail = New clDetail
            objDetail.Kolvo = objRecSetSostav!Range
            objDetail.Massa = objRecSetSostav!Massa
            objDetail.Naimen = objRecSetSostav!Naimen
            objDetail.Obozn = objRecSetSostav!Obozn
            objDetail.Name = objRecSetSostav!Name
            objNode.colDetails.Add objDetail
            objRecSetSostav.MoveNext
         Loop
      End If
   Next
   
   'построение спец-ии
'   If MsgBox("В Excele?", vbQuestion + vbYesNo) = vbNo Then
      SpecSostava colNodes, ListBoxAlboms, ComboBoxSer.Text
'   Else
'      SpecSostavaExcel colNodes, ListBoxAlboms
'   End If

Exit Sub
HasError:
   MsgBox Err.Description, vbCritical, pcsVBProjectName
   
End Sub

Private Sub SpecSostavaExcel(colNodes As Collection, strAlbom As String)
   
   Dim ExcelApp As Excel.Application
   Dim ExcelBook As Excel.Workbook
   Dim ExcelSheet As Excel.Worksheet
   
   Set ExcelApp = CreateObject("Excel.Application")
   Set ExcelBook = ExcelApp.ActiveWorkbook
   ExcelBook.OpenLinks "New"
   ExcelBook.Activate
End Sub

Private Sub SpecSostava(colNodes As Collection, strAlbom As String, strSer As String)
   'построить спеку для этого шифра
   
   Dim objNode As clNode
   Dim objDetail As clDetail
   Dim objTable As AcadTable
   Dim vPtTable As Variant
   Dim intRow As Integer
   Dim colorBad As New AcadAcCmColor
  
   On Error GoTo HasError
   
   FormNodes.Hide
   
   colorBad.ColorMethod = acColorMethodByACI
   colorBad.ColorIndex = acGreen
      
   ThisDrawing.ActiveLayer.LayerOn = True
   ThisDrawing.ActiveLayer.Lock = False
   'запрашиваем точку вставки таблы
   
   vPtTable = ThisDrawing.Utility.GetPoint(, "Верхний левый угол таблицы")
   Set objTable = ThisDrawing.ModelSpace.AddTable(vPtTable, 3, 7, 8, 10)
   'создание стиля таблицы
   MakeTableStyleForSpec
   objTable.StyleName = "Спецификация"
   objTable.RegenerateTableSuppressed = True
   objTable.SetRowHeight 0, 10
   objTable.SetCellValue 0, 0, "Состав соед.элементов в альбоме монт.узлов " & strAlbom & " серии " & strSer & ". Спец-я создана " & VBA.Now
   objTable.SetRowHeight 1, 15
   objTable.SetRowHeight 2, 8
   objTable.SetCellValue 1, 0, "Имя узла"
   objTable.SetColumnWidth 0, 30
   objTable.SetCellValue 1, 1, "Имя детали"
   objTable.SetColumnWidth 1, 40
   objTable.SetCellValue 1, 2, "Наименование"
   objTable.SetColumnWidth 2, 60
   objTable.SetCellValue 1, 3, "Обозначение"
   objTable.SetColumnWidth 3, 40
   objTable.SetCellValue 1, 4, "Кол"
   objTable.SetColumnWidth 4, 10
   objTable.SetCellValue 1, 5, "Масса"
   objTable.SetColumnWidth 5, 15
   objTable.SetCellValue 1, 6, "Примечание"
   objTable.SetColumnWidth 6, 30
   intRow = 1
   
   For Each objNode In colNodes
      'заполняем таблицу
      For Each objDetail In objNode.colDetails
         intRow = intRow + 1
         objTable.InsertRows intRow, 8, 1
         objTable.SetText intRow, 0, objNode.Name
         objTable.SetCellAlignment intRow, 0, acMiddleCenter
         objTable.SetCellTextHeight intRow, 0, 3.5
         objTable.SetText intRow, 1, objDetail.Name
         objTable.SetText intRow, 2, objDetail.Naimen
         objTable.SetText intRow, 3, objDetail.Obozn
         objTable.SetText intRow, 4, objDetail.Kolvo
         objTable.SetCellAlignment intRow, 4, acMiddleCenter
         objTable.SetText intRow, 5, FormatNumber(objDetail.Massa, 2)
         objTable.SetCellAlignment intRow, 5, acMiddleCenter
      Next
      If objNode.colDetails.Count = 0 Then
         intRow = intRow + 1
         objTable.InsertRows intRow, 8, 1
         objTable.SetText intRow, 0, objNode.Name
         objTable.SetCellAlignment intRow, 0, acMiddleLeft
         objTable.SetCellTextHeight intRow, 0, 4
         'подчеркивание пустого узла
         objTable.SetCellContentColor intRow, 0, colorBad
      ElseIf objNode.colDetails.Count > 1 Then
         'объединяем первую колонку с именем узла
         objTable.MergeCells intRow - objNode.colDetails.Count + 1, intRow, 0, 0
      End If
      'толстая нижняя граница
      objTable.SetCellGridLineWeight intRow, 0, AcCellEdgeMask.acBottomMask, AcLineWeight.acLnWt050
      objTable.SetCellGridLineWeight intRow, 1, AcCellEdgeMask.acBottomMask, AcLineWeight.acLnWt050
      objTable.SetCellGridLineWeight intRow, 2, AcCellEdgeMask.acBottomMask, AcLineWeight.acLnWt050
      objTable.SetCellGridLineWeight intRow, 3, AcCellEdgeMask.acBottomMask, AcLineWeight.acLnWt050
      objTable.SetCellGridLineWeight intRow, 4, AcCellEdgeMask.acBottomMask, AcLineWeight.acLnWt050
      objTable.SetCellGridLineWeight intRow, 5, AcCellEdgeMask.acBottomMask, AcLineWeight.acLnWt050
      objTable.SetCellGridLineWeight intRow, 6, AcCellEdgeMask.acBottomMask, AcLineWeight.acLnWt050
   Next
   objTable.ScaleEntity vPtTable, CDbl(TextBoxM)
   objTable.RegenerateTableSuppressed = False
   ThisDrawing.Regen acActiveViewport
   
   FormNodes.Show
   
Exit Sub

HasError:
   Select Case Err.Number
      Case -2147352567 'не указали точку вставки таблы
         FormNodes.Show
      Case Else
         MsgBox Err.Description, vbCritical, pcsVBProjectName
         FormNodes.Show
   End Select
   
End Sub


Private Sub ComboBoxSer_Change()
   
   Dim objRec As New ADODB.Recordset
   Dim strNodeTabl As String
   Dim strBaseTabl As String
   Dim strSql As String
   Dim strSerName As String
   Dim index As Integer
   Dim i As Integer
   
   On Error GoTo HasError
   
' **** Считывание альбомов для выбранной серии ***************
   
   index = ComboBoxSer.ListIndex
   If index = -1 Then
'      MsgBox "Не выбрана серия!", vbCritical
      Exit Sub
   End If
   
   strSerName = ComboBoxSer
   
   'очищаем листбокс
   ListBoxAlboms.Clear
   ListBoxDetails.Clear
   ListBoxNodes.Clear
   'очищаем поля
   TextBoxKol = ""
   TextBoxMassa = ""
   TextBoxNaimen = ""
   TextBoxObozn = ""
   TextBoxNode = ""
   
   LabelPrimech = ComboBoxSer.List(index, 2)
   
   'закрываем Рекордсет
   If objRec.State = adStateOpen Then
      objRec.Close
   End If
   'запрос альбомов
   strSql = "SELECT * FROM Альбомы WHERE Ser_ID = " & ComboBoxSer.List(index, 1) & " ORDER BY Obozn;"
   objRec.Open Source:=strSql, ActiveConnection:=objConect, _
                  CursorType:=adOpenKeyset, LockType:=adLockOptimistic, Options:=adCmdText

   If objRec.EOF And objRec.BOF Then
      'нет Альбоов
      MsgBox "Нет альбомов!", vbInformation, pcsVBProjectName
      Exit Sub
   End If
   'заполняем листбокс альбомов
   objRec.MoveFirst
   Do While Not objRec.EOF
      'Печать поля   записи
      ListBoxAlboms.AddItem objRec!Obozn, i
      ListBoxAlboms.List(i, 1) = objRec!Примечание
      objRec.MoveNext
      i = i + 1
   Loop
   
   ComboBoxSer = strSerName

Exit Sub
HasError:
   MsgBox Err.Description, vbCritical, pcsVBProjectName
         
End Sub

Private Sub ComboBoxSer_Enter()
   ' ******* Cчитывание серий из таблицы Альбомы ***************
   
   Dim objRec As New ADODB.Recordset
   Dim strSql As String
   Dim i As Integer
   
   On Error GoTo HasError
   
   'создаем рекордсет
   'запрос серий Ser из таблицы Серии, с сортировкой по сериям
   strSql = "SELECT * FROM Серии ORDER BY Ser;"
   objRec.Open Source:=strSql, ActiveConnection:=objConect, _
            CursorType:=adOpenKeyset, LockType:=adLockOptimistic, Options:=adCmdText
   'заполняем комбобокс серий
   If objRec.EOF And objRec.BOF Then
      'нет серий в базе
      MsgBox "Нет серий!", vbInformation, pcsVBProjectName
      Exit Sub
   End If
   objRec.MoveFirst
   
   ComboBoxSer.Clear
   i = 0
   Do Until objRec.EOF
      ComboBoxSer.AddItem objRec!Ser, i
      ComboBoxSer.List(i, 1) = objRec!ID
      ComboBoxSer.List(i, 2) = objRec!Примечание
      i = i + 1
      objRec.MoveNext
   Loop
   
Exit Sub
HasError:
   MsgBox Err.Description, vbCritical, pcsVBProjectName
   
End Sub

Private Sub ListBoxAlboms_Click()
   'вывод списка узлов для выбранного альбома, текущей серии
   
   Dim strNodeTabl As String
   Dim strBaseTabl As String
   Dim strSql As String
   Dim i As Integer
   Dim index As Integer
   
   On Error GoTo HasError
   
   index = ListBoxAlboms.ListIndex
   If index = -1 Then
      Exit Sub
   End If
   
   'вывод примечания для выбранного альбома
   LabelPrimech = ListBoxAlboms.List(index, 1)
   
   'очищаем листбокс
   ListBoxDetails.Clear
   ListBoxNodes.Clear
   'очищаем поля
   TextBoxKol = ""
   TextBoxMassa = ""
   TextBoxNaimen = ""
   TextBoxObozn = ""
   TextBoxNode = ""
      
   'закрываем Рекордсет
   If objRecSet.State = adStateOpen Then objRecSet.Close
   'создаем рекордсет
   'запрос узлов для указанного альбома(Obozn) из таблицы узлы
   If ComboBoxSer.Text = "Типовые" Then
      strSql = "SELECT * FROM Типовые_узлы WHERE Obozn = '" & ListBoxAlboms & "' ORDER BY Name;"
   Else
      strSql = "SELECT * FROM Узлы WHERE Obozn = '" & ListBoxAlboms & "' ORDER BY Name;"
   End If
   objRecSet.Open Source:=strSql, ActiveConnection:=objConect, _
                  CursorType:=adOpenKeyset, LockType:=adLockOptimistic, Options:=adCmdText
   If objRecSet.EOF And objRecSet.BOF Then
      'нет узлов в этом альбоме
      MsgBox "Нет узлов!", vbInformation, pcsVBProjectName
      Exit Sub
   End If
   'заполняем листбокс узлов
   objRecSet.MoveFirst
   i = 0
   Do While Not objRecSet.EOF
      'Печать поля   записи
      ListBoxNodes.AddItem objRecSet!Name, i
      ListBoxNodes.List(i, 1) = objRecSet!ID
      If IsNull(objRecSet!Примечание) = False Then
         ListBoxNodes.List(i, 2) = objRecSet!Примечание
      Else
         ListBoxNodes.List(i, 2) = ""
      End If
      i = i + 1
      objRecSet.MoveNext
   Loop

Exit Sub

HasError:
   Select Case Err.Number
      Case Else
         MsgBox Err.Description, vbCritical, pcsVBProjectName
   End Select
   
End Sub

Private Sub ListBoxAlboms_Enter()
   Dim index As Integer
   
   index = ListBoxAlboms.ListIndex
   If index = -1 Then Exit Sub
   
   'вывод примечания для выбранного альбома
   LabelPrimech = ListBoxAlboms.List(index, 1)
   
End Sub

Private Sub ListBoxDetails_Click()
   'для выводим данные по узлу
   
   Dim index As Integer
   Dim strSql As String
   Dim objRecSetTemp As New ADODB.Recordset
   
   On Error GoTo HasError
   
   index = ListBoxDetails.ListIndex
   If index = -1 Then
      'не выбрана деталь
      Exit Sub
   End If
   
   If IsNull(ListBoxDetails.List(index, 3)) Then
      LabelPrimech = ""
   Else
      LabelPrimech = ListBoxDetails.List(index, 3)
   End If
   
   'запрос детали по ее ID
   strSql = "SELECT * FROM Изделия WHERE ID = " & ListBoxDetails.Column(1, index)
   If objRecSet.State = adStateOpen Then objRecSet.Close
   objRecSet.Open Source:=strSql, ActiveConnection:=objConect, _
                     CursorType:=adOpenKeyset, LockType:=adLockOptimistic, Options:=adCmdText
   If objRecSet.EOF And objRecSet.BOF Then
      MsgBox "Деталь не найдена!", vbCritical, pcsVBProjectName
      Exit Sub
   End If
   
   TextBoxKol = ListBoxDetails.Column(2, index)
   TextBoxMassa = objRecSet!Massa
   TextBoxNaimen = objRecSet!Naimen
   TextBoxObozn = objRecSet!Obozn

Exit Sub

HasError:
   Select Case Err.Number
      Case Else
         MsgBox Err.Description, vbCritical, pcsVBProjectName
   End Select
   
End Sub

Private Sub cmbDetailDel_Click()
   'удалить деталь из состава узла
   
   Dim strSql As String
   Dim objRecSetTemp As New ADODB.Recordset
   Dim index As Integer
   Dim indexNode As Integer
   
   On Error GoTo HasError
   
   indexNode = ListBoxNodes.ListIndex
   index = ListBoxDetails.ListIndex
   If index = -1 Then
      'не выбрана деталь
      MsgBox "Не выбран узел!", vbCritical, pcsVBProjectName
      Exit Sub
   End If
   
   'запрос на подтверждение удаления
   If MsgBox("Удалить деталь " & ListBoxDetails, vbYesNo + vbQuestion, pcsVBProjectName) = vbNo Then Exit Sub
   
   'запрос состава узла
   If ComboBoxSer.Text = "Типовые" Then
      strSql = "SELECT * FROM Типовые_состав WHERE Node_ID = " & ListBoxNodes.List(indexNode, 1) & " AND Detail_ID = " & ListBoxDetails.List(index, 1)
   Else
      strSql = "SELECT * FROM Состав WHERE Node_ID = " & ListBoxNodes.List(indexNode, 1) & " AND Detail_ID = " & ListBoxDetails.List(index, 1)
   End If
   objRecSetTemp.Open Source:=strSql, ActiveConnection:=objConect, _
                     CursorType:=adOpenKeyset, LockType:=adLockOptimistic, Options:=adCmdText
   If objRecSetTemp.EOF And objRecSetTemp.BOF Then
      MsgBox "Деталь не найдена!", vbCritical, pcsVBProjectName
      Exit Sub
   End If
   
   objRecSetTemp.Delete
   
   TextBoxKol = ""
   TextBoxMassa = ""
   TextBoxNaimen = ""
   TextBoxObozn = ""
   
   ListBoxDetails.RemoveItem index
   
Exit Sub
HasError:
   MsgBox Err.Description, vbCritical, pcsVBProjectName
   
End Sub

Private Sub ListBoxDetails_MouseDown(ByVal Button As Integer, ByVal Shift As Integer, ByVal X As Single, ByVal Y As Single)
   Dim index As Integer
   
   index = ListBoxDetails.ListIndex
   If index = -1 Then Exit Sub
   
   If IsNull(ListBoxDetails.List(index, 3)) Then
      LabelPrimech = ""
   Else
      LabelPrimech = ListBoxDetails.List(index, 3)
   End If
End Sub

Private Sub ListBoxNodes_Click()
   'вывод инфы по узлу
   
   Dim strNodes As String
   Dim strSql As String
   Dim i As Integer
   Dim objRecSetTemp As New ADODB.Recordset
   Dim index As Integer
   
   On Error GoTo HasError
   
   index = ListBoxNodes.ListIndex
   If index = -1 Then
      'не выделен узел
      Exit Sub
   End If
   
   'выводим примечание для узла
   LabelPrimech = ListBoxNodes.List(index, 2)
   
   strNodes = ListBoxNodes.Text
   'записываем имя выбранного узла
   TextBoxNode = strNodes
   
   'очищаем листбок
   ListBoxDetails.Clear
   'очищаем поля
   TextBoxKol = ""
   TextBoxMassa = ""
   TextBoxNaimen = ""
   TextBoxObozn = ""
   
   If objRecSet.State = adStateOpen Then objRecSet.Close
   'запрос данных по узлу из таблицы состава
   If ComboBoxSer.Text = "Типовые" Then
      strSql = "SELECT Типовые_состав.Примечание, Типовые_состав.Range, Типовые_состав.Detail_ID, Изделия.Name, Изделия.Massa,Изделия.Naimen,Изделия.Obozn,Изделия.Type " & _
         "FROM Типовые_состав INNER JOIN Изделия ON Типовые_состав.Detail_ID = Изделия.ID  " & _
         "WHERE Типовые_состав.Node_ID = " & ListBoxNodes.Column(1, index) & _
         " ORDER BY Изделия.Name;"
   Else
      strSql = "SELECT Состав.Примечание, Состав.Range, Состав.Detail_ID, Изделия.Name, Изделия.Massa,Изделия.Naimen,Изделия.Obozn,Изделия.Type " & _
         "FROM Состав INNER JOIN Изделия ON Состав.Detail_ID = Изделия.ID  " & _
         "WHERE Состав.Node_ID = " & ListBoxNodes.Column(1, index) & _
         " ORDER BY Изделия.Name;"
   End If
   objRecSet.Open Source:=strSql, ActiveConnection:=objConect, _
                     CursorType:=adOpenKeyset, LockType:=adLockOptimistic, Options:=adCmdText
   'заполняем
   If objRecSet.EOF And objRecSet.BOF Then
      'нет деталей в узле
'      MsgBox "В узле нет изделий!", vbInformation
      Exit Sub
   End If
   objRecSet.MoveFirst
   i = 0
   Do Until objRecSet.EOF
      ListBoxDetails.AddItem objRecSet!Name, i
      ListBoxDetails.List(i, 1) = objRecSet!Detail_ID
      ListBoxDetails.List(i, 2) = objRecSet!Range
      If IsNull(objRecSet!Примечание) = False Then
         ListBoxDetails.List(i, 3) = objRecSet!Примечание
      Else
         ListBoxDetails.List(i, 3) = ""
      End If
      objRecSet.MoveNext
      i = i + 1
   Loop
   
Exit Sub

HasError:
   Select Case Err.Number
      Case Else
         MsgBox Err.Description, vbCritical, pcsVBProjectName
   End Select
   
End Sub

Private Sub TextBoxSearchNode_Enter()
   TextBoxSearchNode = ""
End Sub

Private Sub ListBoxNodes_Enter()
   Dim index As Integer
   
   index = ListBoxNodes.ListIndex
   If index = -1 Then Exit Sub
   'выводим примечание для узла
   LabelPrimech = ListBoxNodes.List(index, 2)
   
End Sub

Private Sub UserForm_Initialize()
   'подключение к базе c возможностю редактировать, или только для чтения

   Dim objCommand As New ADODB.Command
   Dim strConect As String
   Dim strMacroFolder As String
   Dim strUsers As String
   
   On Error GoTo HasError
   
' ********** Подключение к базе - Connection *****************
   'для редактирования, или в случае занятости для чтения
   
   If objConect.State = adStateOpen Then
      'подключение уже открыто
      objConect.Close
   End If
   
   strMacroFolder = Funcions.GetMacroFolder(pcsVBProjectName)
   
   'резервная копия базы
'   If Dir(strMacroFolder & "\dbNodes_copy.mdb") <> "" Then
'      Kill strMacroFolder & "\dbNodes_copy.mdb"
'   End If
   
   On Error Resume Next
   
   FileCopy strMacroFolder & "\Базы\dbNodes.mdb", strMacroFolder & "\Базы\dbNodes_copy.mdb"
   'в случае если файл базы редактируется, то скопировать его не получится
   On Error GoTo 0
   
   strUsers = Funcions.ProvBaseNodeState
   
   'строка подключения
   strConect = strProvider & _
            " Dbq=" & strMacroFolder & "\Базы\dbNodes.mdb;"
   'подключение
   objConect.CursorLocation = adUseClient
   objConect.Mode = adModeWrite  'дугие смогут тоже подключатьься
   If strUsers = "" Then
      'если никто не редактирует базу
'      objConect.Mode = adModeWrite  'дугие смогут тоже подключатьься
   Else
      'уведомление о том кто сейчас просматривает каталог тоже
      MsgBox "Каталог сейчас просматривает:" & vbCrLf & strUsers & vbCrLf, vbInformation, pcsVBProjectName
      
'      FormNodes.Caption = FormNodes.Caption & " - только для чтения!"
'      'скрываем кнопки редактирования базы
'      FormNodes.cmbAlbomAdd.Enabled = False
'      FormNodes.cmbAlbomDel.Enabled = False
'      FormNodes.cmbAlbomRename.Enabled = False
'      FormNodes.cmbDetailAdd.Enabled = False
'      FormNodes.cmbDetailDel.Enabled = False
'      FormNodes.cmbNodeAdd.Enabled = False
'      FormNodes.cmbNodeDel.Enabled = False
'      FormNodes.cmbNodeRename.Enabled = False
'      FormNodes.cmbSerAdd.Enabled = False
'      FormNodes.cmbSerDel.Enabled = False
'      FormNodes.cmbSerRename.Enabled = False
'      FormNodes.cmbPrimKolDet.Enabled = False
      
'      objConect.Mode = adModeRead
   End If
   
   objConect.ConnectionString = strConect
   objConect.Open ' strConect
   
'***** Конец подключения Connection *************************
  
  ComboBoxSer_Enter

Exit Sub
HasError:
   Select Case Err.Description
      Case Else
         MsgBox Err.Description, vbCritical, pcsVBProjectName
   End Select

End Sub

Attribute VB_Name = "FormRename"
Attribute VB_Base = "0{EEBFE679-8CA6-4F57-9A83-F74D9F4CA998}{97B6CA46-EAA9-4D40-B544-5E034EDD02E1}"
Attribute VB_GlobalNameSpace = False
Attribute VB_Creatable = False
Attribute VB_PredeclaredId = True
Attribute VB_Exposed = False
Attribute VB_TemplateDerived = False
Attribute VB_Customizable = False
Option Explicit

Dim sNameOld As String

Private Sub cmbCancel_Click()
   bolYes = False
   Hide
End Sub

Private Sub cmbOK_Click()
   On Error GoTo HasError
   If TextBoxName = "" Then
      MsgBox "Пустое имя!", vbCritical, pcsVBProjectName
      Exit Sub
   End If
   TextBoxName = VBA.Trim(TextBoxName)
   'проверка нет ли уже такого узла в серии
   If sNameOld <> TextBoxName Then
    Dim objRec As New ADODB.Recordset
    Dim strSql As String
    Dim sMsgSer As String
    'запрос ID узла
    Dim lSerID As Long
    lSerID = FormNodes.ComboBoxSer.List(FormNodes.ComboBoxSer.ListIndex, 1)
    If FormNodes.ComboBoxSer.Text = "Типовые" Then
       strSql = "SELECT ID FROM Типовые_узлы WHERE Obozn = '" & FormNodes.ListBoxAlboms.Text & "' AND Name = '" & TextBoxName & "';"
       sMsgSer = "Для типовой серии не допускается наличие двух узлов с одним именем в одном альбоме."
    Else
       strSql = "SELECT ID FROM Узлы WHERE Name = '" & TextBoxName & "' AND SerID = " & lSerID & ";"
       sMsgSer = "В нетиповой серии не должно быть двух узлов с одним именем."
    End If
    If objRec.State = adStateOpen Then objRec.Close
    objRec.Open Source:=strSql, ActiveConnection:=objConect, _
          CursorType:=adOpenStatic, LockType:=adLockReadOnly, Options:=adCmdText
    If Not objRec.EOF Or Not objRec.BOF Then
       'такой узел есть
       'сообщеение об ошибке
       MsgBox "Узел с именем " & TextBoxName & " уже есть в альбоме " & FormNodes.ListBoxAlboms.Text & " серии " & FormNodes.ComboBoxSer.Text & "." & vbCrLf & _
              sMsgSer, vbCritical, pcsVBProjectName
       bolYes = False
       Exit Sub
    End If
  End If
   
   bolYes = True
   Hide
Exit Sub
HasError:
   bolYes = False
   MsgBox Err.Description, vbCritical, pcsVBProjectName
End Sub

Private Sub UserForm_Activate()
   On Error Resume Next
   TextBoxName.SetFocus
   sNameOld = TextBoxName
End Sub

Private Sub UserForm_QueryClose(Cancel As Integer, CloseMode As Integer)
   bolYes = False
   Hide
End Sub

Attribute VB_Name = "FormSearchNode"
Attribute VB_Base = "0{59842DEB-6E16-4D56-92E4-106BC95FCF31}{F2B7BF82-9832-46B9-823B-60A2908FE070}"
Attribute VB_GlobalNameSpace = False
Attribute VB_Creatable = False
Attribute VB_PredeclaredId = True
Attribute VB_Exposed = False
Attribute VB_TemplateDerived = False
Attribute VB_Customizable = False
Option Explicit
Dim objRec As New ADODB.Recordset
Dim strSql As String
Dim colSer As New Collection
Dim iSearchCount As Integer

Private Sub cmbSearch_Click()
   On Error GoTo HasError
   iSearchCount = 0
   'ListViewResult.ListItems.Clear
   ListBoxResult.Clear
   
   'поиск в типовой серии
   strSql = "SELECT * FROM Типовые_узлы;" 'WHERE Name Like '" & TextBoxSearchNodeMark & "*';"
   FillListSearch True, strSql, "Name Like '" & TextBoxSearchNodeMark & "*'"
   
   'поиск в наших сериях
   strSql = "SELECT * FROM Узлы;"   'WHERE Name Like '" & TextBoxSearchNodeMark & "*';"
   FillListSearch False, strSql, "Name Like '" & TextBoxSearchNodeMark & "*'"
   
   If iSearchCount = 0 Then
      MsgBox "Поиск завершен. Узлов, марка которых начинается с " & TextBoxSearchNodeMark & ", не найдено.", vbExclamation
      LabelSearchCount = 0
   Else
      'MsgBox "Поиск завершен. Найдено " & iSearchCount & " узлов, марка которых начинается с " & TextBoxSearchNodeMark & ".", vbInformation
      LabelSearchCount = iSearchCount
   End If
   
Exit Sub
HasError:
   MsgBox Err.Description, vbCritical, "FormSearchNode-cmbSearch"
End Sub

Private Function FillListSearch(bTypeSer As Boolean, strSql As String, sFilter As String)
   On Error GoTo HasError
   'Dim oListItem As MSComctlLib.ListItem
   
   If objRec.State = adStateOpen Then objRec.Close
   Funcions.OpenRecordSet objRec, strSql
   objRec.Filter = sFilter
   If objRec.EOF And objRec.BOF Then
      'узлы не найдены
      Exit Function
   End If
   
   objRec.MoveFirst
   Do While Not objRec.EOF
      'Set oListItem = ListViewResult.ListItems.Add(, , objRec.Fields("Name").Value)
      ListBoxResult.AddItem objRec!Name, 0
      ListBoxResult.List(0, 1) = objRec!Obozn ' oListItem.SubItems(1) = objRec.Fields("Obozn").Value
      If bTypeSer Then
         'oListItem.SubItems(2) = "Типовая"
         ListBoxResult.List(0, 2) = objRec!Obozn
      Else
         'oListItem.SubItems(2) = colSer.Item("'" & objRec.Fields("SerID").Value & "'")
         ListBoxResult.List(0, 2) = colSer.Item("'" & objRec!SerID & "'")
      End If
      objRec.MoveNext
      iSearchCount = iSearchCount + 1
   Loop
Exit Function
HasError:
   MsgBox Err.Description, vbCritical, "FormSearchNode-FillListSearch"
End Function

Private Sub UserForm_Initialize()
   'список серий и их ID
   FillSer
   
'   ListViewResult.ColumnHeaders.Add , , "Марка", 45, 0, 0
'   ListViewResult.ColumnHeaders.Add , , "Обозначение", 95, 0, 0
'   ListViewResult.ColumnHeaders.Add , , "Серия", 65, 0, 0
End Sub

Private Function FillSer()
   On Error GoTo HasError
   'запрос серий Ser из таблицы Серии
   strSql = "SELECT ID, Ser FROM Серии;"
   If objRec.State = adStateOpen Then objRec.Close
   Funcions.OpenRecordSet objRec, strSql
   If objRec.EOF And objRec.BOF Then
      'нет серий в базе
      Exit Function
   End If
   objRec.MoveFirst
   Do Until objRec.EOF
      colSer.Add objRec.Fields("Ser").Value, "'" & objRec.Fields("ID").Value & "'"
      objRec.MoveNext
   Loop
Exit Function
HasError:
   MsgBox Err.Description, vbCritical, "FormSearchNode-FillSer"
End Function

Attribute VB_Name = "FormSer"
Attribute VB_Base = "0{6DB3F626-C5C3-4278-9A56-7AA037C9EC82}{9EAB7F6A-A97E-48ED-8E52-78EADB71C85E}"
Attribute VB_GlobalNameSpace = False
Attribute VB_Creatable = False
Attribute VB_PredeclaredId = True
Attribute VB_Exposed = False
Attribute VB_TemplateDerived = False
Attribute VB_Customizable = False
Option Explicit

Private Sub cmbOK_Click()
   
   If ComboBoxSer.ListIndex = -1 Then
      MsgBox "Нужно выбрать серию!", vbCritical, pcsVBProjectName
      Exit Sub
   End If
   
   'проверяем масштаб на соответствие числу doubles
   If Not IsNumeric(TextBoxM) Then
      MsgBox "Масштаб не верный. Должно быть число!", vbCritical, pcsVBProjectName
      Exit Sub
   End If
   
   Hide
   
End Sub

Private Sub CommandButton1_Click()
   End
End Sub

Attribute VB_Name = "Funcions"
Option Explicit

Public Function GetMacroFolder(pcsVBProjectName) As String
   'получение пути к корню макроса
   'без \
   
   Dim strMacroFolder As String
   Dim intValue As Integer
   
   On Error GoTo HasError
   
   strMacroFolder = Application.VBE.vbprojects.Item(pcsVBProjectName).FileName
   intValue = InStrRev(strMacroFolder, "\")
   strMacroFolder = VBA.Left(strMacroFolder, intValue - 1) 'корень с макросом, без \ на конце
   
   GetMacroFolder = strMacroFolder
   
Exit Function

HasError:
   Select Case Err.Number
      Case Else
         MsgBox "Functions, GetMacroFolder" & vbCrLf & _
               Err.Description, vbCritical, pcsVBProjectName
   End Select
   
End Function

Public Function ProvBaseNodeState() As String
   'проверка статуса базы узлов
   'при редактировании базы появляется файл dbNodes.ldb рядом с осеовным файлом базы, его и нужно посмотреть
   'ИмяПользователя - если база редактируется
   '"" - если нет
   
   Dim strLBDNodesFullPath As String
   Dim strBDNodesFolder As String
   Dim strMacroFolder As String
   Dim strValue As String
   Dim intValue As Integer
   
   'путь к этому проекту: \\Sgpsrv2\СПД\Конструкторы\Макросы\SpecKonstr\SpecKonstr.dvb
   strMacroFolder = GetMacroFolder(pcsVBProjectName)
   'надо получить: \\Sgpsrv2\СПД\Конструкторы\Макросы\BaseNodes\dbNodes.ldb
   intValue = InStrRev(strMacroFolder, "\")
   intValue = InStrRev(strMacroFolder, "\", intValue + 1)
   strValue = VBA.Left(strMacroFolder, intValue) 'без имени SpecKonstr\SpecKonstr.dvb, т.е \\Sgpsrv2\СПД\Конструкторы\Макросы\
   strBDNodesFolder = strValue & "BaseNodes"
   strLBDNodesFullPath = strBDNodesFolder & "\dbNodes.ldb"
   'проверяем есть ли такой файл
   If Dir(strLBDNodesFullPath) = "" Then
      'нет такого файла
      ProvBaseNodeState = ""
   Else
      Err.Clear
      On Error Resume Next
      'попробую удалить, может это старый файл
      Kill strLBDNodesFullPath
      On Error GoTo 0
      If Not Err Then
         'т.е. файл удалился, и был старым
         ProvBaseNodeState = ""
      End If
      'нужно его открыть и прочитать первую строчку
      Open strLBDNodesFullPath For Input As #1
        Input #1, strValue
      Close #1
      If strValue <> "" Then
         'нужно выцепить из строчки имя пользователя
         ProvBaseNodeState = strValue
      Else
         'тогда не знаю что
         ProvBaseNodeState = strValue
      End If
   End If
   
End Function


Public Function GetLayerName(strLayer As String) As String
   'возвращаем имя существующего слоя
   Dim objLayer As AcadLayer
   
   On Error GoTo HasError
   GetLayerName = ThisDrawing.Layers.Item(strLayer)
   
Exit Function
HasError:
   ThisDrawing.Layers.Add strLayer
   GetLayerName = strLayer
End Function

Public Function MakeTableStyleForSpec() As String
   'создание табличного стиля для спецификаций
   'для масштаба 1:1, в конкретных условиях нужно отмасштабировать после заполнения
   
   Const strTableStyleName = "Спецификация"
   Const strTextStyleName = "Спецификаций"
   
   Dim objTableStyle As AcadTableStyle
   Dim objTextStyle As AcadTextStyle
   Dim objDictTableStyle As AcadDictionary
   Dim bolYes As Boolean
   
   'создаем табличный стиль в словаре чертежа
   Set objDictTableStyle = ThisDrawing.Dictionaries.Item("ACAD_TABLESTYLE")
   
   'проверяем есть ли уже такой табл стиль
   For Each objTableStyle In objDictTableStyle
      If objTableStyle.Name = strTableStyleName Then
         'переделывать не буду ????????????
         Exit Function
      End If
   Next
'   On Error Resume Next 'не хорошо конечно, надо сделать проверки
   Set objTableStyle = objDictTableStyle.AddObject(strTableStyleName, "AcDbTableStyle")
   
   'создаем текстовый стиль для таблиц
   For Each objTextStyle In ThisDrawing.TextStyles
      If objTextStyle.Name = strTextStyleName Then
         bolYes = True
      End If
   Next
   If bolYes = False Then
      Set objTextStyle = ThisDrawing.TextStyles.Add(strTextStyleName)
      'задаем шрифт, у нас принят ариал
      objTextStyle.SetFont "Arial", False, False, 0, 34 'значения получил по GetFont для нужного стиля
   End If
'   On Error GoTo 0

   'настраиваем таблицу
   'задаем текстовый стиль всем типам ячеек
   objTableStyle.SetTextStyle AcRowType.acDataRow + AcRowType.acHeaderRow _
                           + AcRowType.acTitleRow + AcRowType.acUnknownRow, strTextStyleName
   'задаем высоту текста
   objTableStyle.SetTextHeight AcRowType.acDataRow + AcRowType.acUnknownRow, 2.5
   objTableStyle.SetTextHeight AcRowType.acHeaderRow + AcRowType.acTitleRow, 3
   'задаем выравниваниев ячейках
   objTableStyle.SetAlignment AcRowType.acHeaderRow + AcRowType.acTitleRow, acMiddleCenter
   objTableStyle.SetAlignment AcRowType.acDataRow + AcRowType.acUnknownRow, acMiddleLeft
   'задаем отступы в ячейках
   objTableStyle.HorzCellMargin = 1.5
   objTableStyle.VertCellMargin = 1
   'задаем толщины границ
   objTableStyle.SetGridLineWeight AcGridLineType.acHorzBottom + AcGridLineType.acHorzInside + AcGridLineType.acHorzTop _
                + AcGridLineType.acVertInside + AcGridLineType.acVertLeft + AcGridLineType.acVertRight, _
                AcRowType.acTitleRow + AcRowType.acHeaderRow, AcLineWeight.acLnWt050
   objTableStyle.SetGridLineWeight AcGridLineType.acHorzBottom + AcGridLineType.acHorzTop + _
               AcGridLineType.acVertInside + AcGridLineType.acVertLeft + AcGridLineType.acVertRight, _
               AcRowType.acDataRow + AcRowType.acUnknownRow, AcLineWeight.acLnWt050
   objTableStyle.SetGridLineWeight AcGridLineType.acHorzInside, _
               AcRowType.acDataRow + AcRowType.acUnknownRow, AcLineWeight.acLnWt025
   'задаем цвет тексту
   Dim color As New AcadAcCmColor
   color.SetRGB 255, 0, 0
   objTableStyle.SetColor AcRowType.acDataRow + AcRowType.acHeaderRow _
                        + AcRowType.acTitleRow + AcRowType.acUnknownRow, color
   
   'вроде все, посмотрим
   
   'возвращаем имя созданного стиля
   MakeTableStyleForSpec = strTableStyleName
   
End Function

Public Function GetTfromListName(arrayListName() As String) As Variant
   'получить массив толщин пластин из их имен (8x30x60)
   'возвращает массив чисел
   
   Dim i As Integer
   Dim j As Integer
   Dim intValue As Integer
   Dim aiT() As Integer
   Dim intT As Integer
   Dim bolIn As Boolean
   
   Dim varVal As Variant
   For i = 0 To UBound(arrayListName)
      intT = Val(arrayListName(i))
      If i = 0 Then
         ReDim aiT(0)
         aiT(0) = intT
      Else
         intValue = UBound(aiT)
         bolIn = False
         For j = 0 To intValue
            If intT = aiT(j) Then
               bolIn = True
               Exit For
            End If
         Next
         If bolIn = False Then
            ReDim Preserve aiT(intValue + 1)
            aiT(intValue + 1) = intT
         End If
      End If
   Next
   
   GetTfromListName = aiT
   
End Function

Public Function GetWidthFromListName(arrayListName() As String) As Variant
   'получить массив ширин пластин из их имен (8x30x60)
   'возвращает массив чисел
   
   Dim i As Integer
   Dim j As Integer
   Dim intValue As Integer
   Dim aiWidth() As Integer
   Dim intWidth As Integer
   Dim strValue As String
   Dim bolIn As Boolean
   
   For i = 0 To UBound(arrayListName)
      intValue = InStr(arrayListName(i), "x")
      strValue = (VBA.Mid(arrayListName(i), intValue + 1))
      intValue = InStr(arrayListName(i), "x")
      intWidth = Val(strValue)
      If i = 0 Then
         ReDim aiWidth(0)
         aiWidth(0) = intWidth
      Else
         intValue = UBound(aiWidth)
         bolIn = False
         For j = 0 To intValue
            If intWidth = aiWidth(j) Then
               bolIn = True
               Exit For
            End If
         Next
         If bolIn = False Then
            ReDim Preserve aiWidth(intValue + 1)
            aiWidth(intValue + 1) = intWidth
         End If
      End If
   Next
   
   GetWidthFromListName = aiWidth
   
End Function

'изменение разделителя целой и дробной части
Public Function ReplaceDelimiter(InputStr As String) As String
   Dim objReg As New clReg
   Dim strDelim As String
      objReg.oprRootKeyName = rkn_HKEY_CURRENT_USER
      strDelim = objReg.oprRegGetVal("\Control Panel\International\sDecimal")
    InputStr = Replace(InputStr, ".", strDelim)
    InputStr = Replace(InputStr, ",", strDelim)
    ReplaceDelimiter = InputStr
End Function

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function


Public Function SortyrColNodeAndObozn(colNodesAndObozn As Collection) As Collection
   'сортировка коллекции объектов clNodeAndObozn
   
   Dim objClNodeAndOboznTemp As clNodeAndObozn
   Dim i As Integer
   Dim j As Integer
   
   Set SortyrColNodeAndObozn = New Collection
   
   For i = 1 To colNodesAndObozn.Count - 1
      For j = 1 To colNodesAndObozn.Count - i
         If StrComp(colNodesAndObozn.Item(j).Name, colNodesAndObozn.Item(j + 1).Name, vbTextCompare) = 1 Then
            Set objClNodeAndOboznTemp = colNodesAndObozn.Item(j).Name
            colNodesAndObozn.Remove j
            colNodesAndObozn.Add objClNodeAndOboznTemp, objClNodeAndOboznTemp.Name & objClNodeAndOboznTemp.Obozn, , j
         End If
      Next
   Next
   
   Set SortyrColNodeAndObozn = colNodesAndObozn

End Function

Public Function OpenRecordSet(oRecSet As ADODB.Recordset, sSql As String)
   oRecSet.Open Source:=sSql, ActiveConnection:=objConect, _
            CursorType:=adOpenKeyset, LockType:=adLockOptimistic, Options:=adCmdText
End Function

Attribute VB_Name = "Main"
Option Explicit
      
   Public objConect As New ADODB.Connection
   Public bolYes As Boolean
   Public Const strProvider As String = "Driver={Microsoft Access Driver (*.mdb, *.accdb)};" ' "Provider=Microsoft.Jet.OLEDB.4.0;"
   Public Const pcsVBProjectName As String = "BaseNodes"
   Public psSerForInsNode As String

Public Sub BaseNodes()
   
   On Error GoTo HasError
   
   'редактирование базы узлов
   FormNodes.Show
   
   End

Exit Sub
HasError:
  MsgBox Err.Description, vbCritical, pcsVBProjectName
End Sub

'Public Sub BaseDetails()
'   'редактирование базы деталей
'
'   Dim objCommand As New ADODB.Command
'   Dim strConect As String
'   Dim strMacroFolder As String
'
'   'строка подключения
'   If Not objConect.State = adStatusOK Then
'      strMacroFolder = Funcions.GetMacroFolder(pcsVBProjectName)
'      strConect = strProvider & _
'               "Data Source=" & strMacroFolder & "\dbNodes.mdb"
'      'подключение
'      objConect.Mode = adModeWrite
'      objConect.Open strConect
'
'      If Not objConect.State = adStatusOK Then
'         'подключится не удалось
'         MsgBox "Подключиться с полным доступом к базе не удалось"
'         End
'      End If
'   End If
'
'   'скрываем кнопку ОК, будет только закрыть
'   FormDetails.cmbOK.Visible = False
'
'   FormDetails.Show
'
'   objConect.Close
'
'End Sub

Public Sub InsertNode()
   'вставка блоков узлов в чертеж
   
   Dim objCommand As New ADODB.Command
   Dim objRecSet As New ADODB.Recordset
   Dim strConect As String
   Dim strSql As String
   Dim strMacroFolder As String
   Dim strNodeDWGFullPath As String
   Dim objBlNode As AcadBlockReference
   Dim varPt As Variant
   Dim varAtr As Variant
   Dim objAtr As AcadAttributeReference
   Dim strLayer As String
   Dim i As Integer
   
   On Error GoTo HasError
   
   'подлючение к базе
   If objConect.State = adStatusOK Then objConect.Close
   
   strMacroFolder = Funcions.GetMacroFolder(pcsVBProjectName)
   strConect = strProvider & " Dbq=" & strMacroFolder & "\Базы\dbNodes.mdb;"
   'подключение
   objConect.CursorLocation = adUseClient
   objConect.Mode = adModeRead
   objConect.ConnectionString = strConect
   objConect.Open 'strConect
   
   'запрос серий
   If objRecSet.State = adStateOpen Then objRecSet.Close
   strSql = "SELECT * FROM Серии WHERE Ser <> 'Типовые';"
   objRecSet.Open Source:=strSql, ActiveConnection:=objConect, _
            CursorType:=adOpenKeyset, LockType:=adLockOptimistic, Options:=adCmdText
   'заполняем комбобок серий в FormSer
   If objRecSet.EOF And objRecSet.BOF Then
      MsgBox "Серий нет! Создайте серию в каталоге узлов!", vbCritical, pcsVBProjectName
      Exit Sub
   End If
   objRecSet.MoveFirst
   FormSer.ComboBoxSer.Clear
   Do Until objRecSet.EOF
      FormSer.ComboBoxSer.AddItem objRecSet!Ser
      objRecSet.MoveNext
   Loop
   'форма для выбора серии
   FormSer.Show
   
   psSerForInsNode = FormSer.ComboBoxSer
   
   'заполнение комбобокса обозначений из таблицы Альбомов в FormInsNode
   'запрос альбомов для выбранной серии
   If objRecSet.State = adStateOpen Then objRecSet.Close
   strSql = "SELECT Альбомы.Obozn, Серии.Ser FROM Серии INNER JOIN Альбомы ON Серии.ID = Альбомы.Ser_ID " & _
         "WHERE Серии.Ser In ('Типовые','" & psSerForInsNode & "')ORDER BY Альбомы.Obozn;"
   objRecSet.Open Source:=strSql, ActiveConnection:=objConect, _
            CursorType:=adOpenKeyset, LockType:=adLockOptimistic, Options:=adCmdText
   If objRecSet.EOF And objRecSet.BOF Then
      MsgBox "Альбомов нет! Создайте новый альбом в каталоге узлов!", vbCritical, pcsVBProjectName
      Exit Sub
   End If
   'заполняем комбобокс серий в FormSer
   objRecSet.MoveFirst
   FormInsNode.ComboBoxObozn.Clear
   FormInsNode.ComboBoxObozn.AddItem "Все"
   i = 1
   Do Until objRecSet.EOF
      FormInsNode.ComboBoxObozn.AddItem objRecSet!Obozn
      FormInsNode.ComboBoxObozn.List(i, 1) = objRecSet!Ser
      objRecSet.MoveNext
      i = i + 1
   Loop
   
   'создаем слой Блоковузлов
   strLayer = Funcions.GetLayerName("Блоки узлов")
   
   'форма выбора узла и вставки блока в чертеж
   FormInsNode.Show vbModeless
   
Exit Sub

HasError:
   Select Case Err.Number
      Case Else
         MsgBox Err.Description, vbCritical, pcsVBProjectName
   End Select
End Sub

Public Sub DelTabledb()
   
   Dim objCommand As New ADODB.Command
   
   Dim objCatalog As New ADOX.Catalog
   Dim objTable As New ADOX.Table
   Dim strConect As String
   Dim strMacroFolder As String
   Dim strBDTempPath As String
   
   'создаем копию базы, в [макрос]\Temp\dbNodes_temp.mdb
   strMacroFolder = Funcions.GetMacroFolder(pcsVBProjectName)
   strBDTempPath = strMacroFolder & "\Temp"
   If Dir(strBDTempPath, vbDirectory) = "" Then
      MkDir strBDTempPath
   End If
   FileCopy strMacroFolder & "\Базы\dbNodes.mdb", strBDTempPath & "\Базы\dbNodes_temp.mdb"
   
   'подлючение к базе
   If objConect.State = adStatusOK Then objConect.Close
   
   strConect = strProvider & _
            "Data Source=" & Funcions.GetMacroFolder(pcsVBProjectName) & "\Базы\dbNodes.mdb"
   'подключение
   objConect.Mode = adModeWrite
   objConect.IsolationLevel = adXactIsolated
   objConect.CursorLocation = adUseClient
   objConect.ConnectionString = strConect
   objConect.Open 'strConect

   objCommand.ActiveConnection = objConect
   objCommand.CommandType = adCmdText
   'удаляем связь Альбом - узлы
   objCommand.CommandText = "ALTER TABLE 12_узлы DROP CONSTRAINT [Связь_альбом_12]"
   objCommand.Execute
   'удаляем связь узлы - состав
   objCommand.CommandText = "ALTER TABLE 12_состав DROP CONSTRAINT [Связь_узел_12]"
   objCommand.Execute
   'удаляем связь состав - изделия
   objCommand.CommandText = "ALTER TABLE 12_состав DROP CONSTRAINT [Связь_12]"
   objCommand.Execute
   'удаляем таблицу узлов
   objCommand.CommandText = "DROP TABLE [12_узлы]"
   objCommand.Execute
   'удаляем таблицу состава
   objCommand.CommandText = "DROP TABLE [12_состав]"
   objCommand.Execute
   
   'подключение к базе через ADOX
   objCatalog.ActiveConnection = objConect
   
   'удаляем таблу "ИмяСер_узлы"
   'удаляем ключ из табл Альбомы
   Set objTable = objCatalog.Tables("Альбомы")
   objTable.Keys.Delete ("Составной")
   Set objTable = objCatalog.Tables("12_узлы")
   'удаляем связь
   objCatalog.Tables.Delete ("12_узлы")
   'удаляем таблу "ИмяСер_состав"
   objCatalog.Tables.Delete ("12_состав")
   
End Sub

Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit


Public Sub SelBlNode()
   'выбор всех блоклв узлов с обозн=Все
   
   Dim objBlNode As AcadBlockReference
   Dim selSet As AcadSelectionSet
   Dim varAtr As Variant
   Dim intCodeType(1) As Integer
   Dim varCodeDate(1) As Variant
   Dim intKolDelNodes As Integer
     
   Set selSet = Funcions.GetSelSet("Узлы")
   
   intCodeType(0) = 0: varCodeDate(0) = "insert"
   intCodeType(1) = 2: varCodeDate(1) = "Узел"
   
   selSet.Select acSelectionSetAll, , , intCodeType, varCodeDate
   
   For Each objBlNode In selSet
      For Each varAtr In objBlNode.GetAttributes
         If LCase(varAtr.TagString) = "обозначение" Then
            If LCase(varAtr.TextString) = "все" Then
               objBlNode.Delete
               intKolDelNodes = intKolDelNodes + 1
            End If
         End If
      Next
   Next
   
   MsgBox intKolDelNodes & " - удалено", vbInformation, pcsVBProjectName
   
End Sub

Attribute VB_Name = "clDetail"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'данные по детале
   
   Dim strName As String
   Dim strUniqName As String
   Dim strNaimen As String
   Dim strObozn As String
   Dim dMassa As Double
   Dim intKolvo As Integer

'имя жетали (МС1)
Public Property Get Name() As String
   Name = strName
End Property
Public Property Let Name(ByVal vNewValue As String)
   strName = vNewValue
End Property

'наименовани : Изделие соед
Public Property Get Naimen() As String
   Naimen = strNaimen
End Property
Public Property Let Naimen(ByVal vNewValue As String)
   strNaimen = vNewValue
End Property

'обозначение : 5463-1-АС.У
Public Property Get Obozn() As String
   Obozn = strObozn
End Property
Public Property Let Obozn(ByVal vNewValue As String)
   strObozn = vNewValue
End Property

'масса - 0.16
Public Property Get Massa() As Double
   Massa = dMassa
End Property
Public Property Let Massa(ByVal vNewValue As Double)
   dMassa = vNewValue
End Property

'кол-во деталей
Public Property Get Kolvo() As Integer
   Kolvo = intKolvo
End Property
Public Property Let Kolvo(ByVal vNewValue As Integer)
   intKolvo = vNewValue
End Property

Attribute VB_Name = "clNode"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'данные по узлу

   Public colDetails As New Collection
   
   Dim strName As String
   Dim strObozn As String
   Dim intKolvo As Integer
   Dim lID As Long

'имя узла
Public Property Get Name() As String
   Name = strName
End Property
Public Property Let Name(ByVal vNewValue As String)
   strName = vNewValue
End Property

'обозначение - 5463-1-АС
Public Property Get Obozn() As String
   Obozn = strObozn
End Property
Public Property Let Obozn(ByVal vNewValue As String)
   strObozn = vNewValue
End Property

'ID узла
Public Property Get ID() As Long
   ID = lID
End Property
Public Property Let ID(ByVal vNewValue As Long)
   lID = vNewValue
End Property


'кол-во блоков на чертеже
Public Property Get Kolvo() As Integer
   Kolvo = intKolvo
End Property
Public Property Let Kolvo(ByVal vNewValue As Integer)
   intKolvo = vNewValue
End Property

Attribute VB_Name = "clReg"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'класс полностью спёрт, без изменений!

'К сожалению перечисления только для чисел типа Long
'Для перевода в строку воспользуемся функцией-конвертор ConverterRootKeyName()
'Т.к. начинаем отсчет с 0, то по умолчанию будет первичный раздел HKEY_CURRENT_USER
Public Enum RootKeyName
   rkn_HKEY_CURRENT_USER
   rkn_HKEY_LOCAL_MACHINE
   rkn_HKEY_CLASSES_ROOT
   rkn_HKEY_USERS
   rkn_HKEY_CURRENT_CONFIG
   rkn_HKEY_DYN_DATA
   'rkn_HKEY_PERFORMANCE_DATA
End Enum

Private WSHShell As Object
Private rknRootKeyName As RootKeyName 'Корневой раздел

'/////////////// С В О Й С Т В А ///////////////

' Версия
Public Property Get oprVersion() As String
oprVersion = "2.10.030916 L"
End Property

'Ключ автозагрузки
Public Property Get oprStartup() As String
oprStartup = "SoftwareMicrosoftWindowsCurrentVersionRun"
End Property

Public Property Get oprRootKeyName() As RootKeyName
oprRootKeyName = rknRootKeyName
End Property
Public Property Let oprRootKeyName(rknNewValue As RootKeyName)
rknRootKeyName = rknNewValue
End Property


'/////////////// С О Б Ы Т И Я ///////////////
Private Sub Class_Initialize()
Set WSHShell = CreateObject("WScript.Shell")
End Sub


Private Sub Class_Terminate()
Set WSHShell = Nothing
End Sub



'/////////////// М Е Т О Д Ы ///////////////

' Функция oprRegGetVal() возврвщает значение ключа реестра
Public Function oprRegGetVal(strSubKey As String) As Variant
On Error GoTo oprRegGetVal_Error

Dim strName As String, varResult As Variant

strName = CompletePath(strSubKey)
varResult = WSHShell.RegRead(strName)

oprRegGetVal_Exit:
oprRegGetVal = varResult
Exit Function

oprRegGetVal_Error:
If Err.Number = -2147024894 Then varResult = ""
Resume oprRegGetVal_Exit
End Function


' Процедура oprRegWriteVal() создает раздел / параметр.
Public Sub oprRegWriteVal(strSubKey As String, varValue As Variant)
Dim strName As String

strName = CompletePath(strSubKey)
WSHShell.RegWrite strName, varValue
End Sub


' Процедура oprRegDelete() Удаляет раздел / параметр.
Public Sub oprRegDelete(strSubKey As String)
On Error GoTo oprRegGetVal_Error

Dim strName As String

strName = CompletePath(strSubKey)
WSHShell.RegDelete (strName)

oprRegGetVal_Exit:
Exit Sub

oprRegGetVal_Error:
If Err.Number = -2147024894 Then
Else
MsgBox Err.Description, vbCritical, pcsVBProjectName
End If
Resume oprRegGetVal_Exit
End Sub


' Процедура oprStartupAdd() Создает новый параметр автозагрузки.
Public Sub oprStartupAdd(strProgramName As String, strPathProgram As String)
Dim strSubKey As String, rknRootKeyName As RootKeyName

strSubKey = Me.oprStartup & strProgramName

rknRootKeyName = Me.oprRootKeyName

Me.oprRootKeyName = rkn_HKEY_LOCAL_MACHINE
Me.oprRegWriteVal strSubKey, strPathProgram

Me.oprRootKeyName = rknRootKeyName
End Sub


' Процедура oprStartupDelete() Удаляет параметр автозагрузки.
Public Sub oprStartupDelete(strProgramName As String)
Dim strSubKey As String, rknRootKeyName As RootKeyName

strSubKey = Me.oprStartup & strProgramName

rknRootKeyName = Me.oprRootKeyName

Me.oprRootKeyName = rkn_HKEY_LOCAL_MACHINE
Me.oprRegDelete strSubKey

Me.oprRootKeyName = rknRootKeyName
End Sub



'/////////////// Д О П . Ф У Н К Ц И И ///////////////

' Функция ConverterRootKeyName() возврвщает значение типа строка
Private Function ConverterRootKeyName(lngKey As Long) As String
Dim strKeyName As String
Select Case lngKey
Case 0
strKeyName = "HKCU"
Case 1
strKeyName = "HKLM"
Case 2
strKeyName = "HKCR"
Case 3
strKeyName = "HKEY_USERS"
Case 4
strKeyName = "HKEY_CURRENT_CONFIG"
Case 5
strKeyName = "HKEY_DYN_DATA"
Case 6
strKeyName = "HKEY_PERFORMANCE_DATA"
Case Else
strKeyName = ""
End Select

ConverterRootKeyName = strKeyName
End Function


' Функция CompletePath() возврвщает полный путь к параметру
Private Function CompletePath(strPathKey As String) As String
Dim strName As String

strName = VBA.Left(strPathKey, 1)

' Добавим обратный слеж если его нет
If strName = "" Then
strName = ConverterRootKeyName(Me.oprRootKeyName) & strPathKey
Else
strName = ConverterRootKeyName(Me.oprRootKeyName) & "" & strPathKey
End If

CompletePath = strName
End Function
