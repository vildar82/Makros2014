Attribute VB_Name = "FormSelectTextWithNumber"
Attribute VB_Base = "0{CB84A288-1346-430F-BD72-6E8C745CA0D9}{84EA8CAE-3D7D-4F7E-93A0-0B722FA76952}"
Attribute VB_GlobalNameSpace = False
Attribute VB_Creatable = False
Attribute VB_PredeclaredId = True
Attribute VB_Exposed = False
Attribute VB_TemplateDerived = False
Attribute VB_Customizable = False
Option Explicit

Private Sub cmbSelect_Click()
   
   Dim oEnt As AcadEntity
   Dim oText As AcadText
   Dim value As Double
   Dim cond As Double
   Dim aobjEnt() As AcadEntity
   Dim colTexts As New Collection
   Dim i As Integer
   Dim selset As AcadSelectionSet
   
   On Error GoTo HasError
   
   Me.Hide
   
   cond = Val(TextBoxMinNum)
   TextBoxMinNum = cond
   
   'пройтись по объектам модели и выбрать тектовые объекты
   For Each oEnt In ThisDrawing.ModelSpace
      If TypeOf oEnt Is AcadText Then
         Set oText = oEnt
         value = Val(oText.TextString)
         If value >= cond Then
            colTexts.Add oEnt
         End If
      End If
   Next
   
   ReDim aobjEnt(colTexts.Count - 1)
   
   'заносим все выноски из коллекции в массив
   i = 0
   For Each oEnt In colTexts
      Set aobjEnt(i) = oEnt
      i = i + 1
   Next
   
   'определяем набор, для выносок, и передачи в лисп(для подсветки)
   Set selset = Functions.GetSelSet("Подсветка")
   'заносим выноски в набор
   selset.AddItems aobjEnt
   
   'лисповская функция для подсветки набора "Подсветка"
   'ThisDrawing.SendCommand "(vl-load-com)" & vbCr
   ThisDrawing.SendCommand "(selset-gripset)" & vbCr
   
Exit Sub
HasError:
   MsgBox Err.Description, vbCritical, "SelectText"
End Sub

Private Sub UserForm_Click()

End Sub
Dim aobjEnt() As AcadEntity
   Dim objEnt As AcadEntity
   Dim i As Integer
   
   Set objListItem = ListView1.SelectedItem
   If objListItem Is Nothing Then Exit Sub
   
   'получаем выбранную выноску из коллекции
   Set objClNode = colNodeAndName.Item(objListItem.Text)
   
   'переопределяем массив выносок
   ReDim aobjEnt(objClNode.colNodeEntity.Count - 1)
   
   'заносим все выноски из коллекции в массив
   For Each objEnt In objClNode.colNodeEntity
      Set aobjEnt(i) = objEnt
      i = i + 1
   Next
   
   'определяем набор, для выносок, и передачи в лисп(для подсветки)
   Set selSetNodes = Functions.GetSelSet("Подсветка")
   'заносим выноски в набор
   selSetNodes.AddItems aobjEnt
   
   'лисповская функция для подсветки набора "Подсветка"
   ThisDrawing.SendCommand "(selset-gripset)" & vbCr

Attribute VB_Name = "Functions"
Option Explicit

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function GetMacroFolder(strVBProjectName) As String
   'получение пути к корню макроса
   'без \
   Dim strMacroFolder As String
   Dim intValue As Integer
   
   On Error GoTo HasError
   
   strMacroFolder = Application.VBE.vbprojects.Item(strVBProjectName).FileName
   intValue = InStrRev(strMacroFolder, "\")
   strMacroFolder = Left(strMacroFolder, intValue - 1) 'корень с макросом, без \ на конце
   
   GetMacroFolder = strMacroFolder
   
Exit Function

HasError:
   Select Case Err.Number
      Case Else
         MsgBox "Functions, GetMacroFolder" & vbCrLf & _
               Err.Description
   End Select
   
End Function

Attribute VB_Name = "Main"
Option Explicit
Public Const psVBprojectName As String = "SelectTextWithCondNumber"

Public Sub Main()
   On Error GoTo HasError
   
   LoadLsp
   
   FormSelectTextWithNumber.Show
   
Exit Sub
HasError:
   MsgBox Err.Description, vbCritical, "SelectText"
   
End Sub

Private Function LoadLsp()
   Dim strLispFullPath As String
   Dim strCom As String
   'загружаем лисп файл
   'определяем полный путь к файлу
   strLispFullPath = Functions.GetMacroFolder(psVBprojectName)
   strLispFullPath = strLispFullPath & "\SpdsNode.fas"
   strLispFullPath = Replace(strLispFullPath, "\", "/")
   'загружаем лисп файл SpdsNode.lsp из корня с макросом этого проекта
   strCom = "(load " & Chr(34) & strLispFullPath & Chr(34) & ")"
   ThisDrawing.SendCommand strCom & vbCr
   'нужно как-то проверить загрузился ли
   
End Function
