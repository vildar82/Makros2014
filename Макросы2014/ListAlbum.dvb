Attribute VB_Name = "Album"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public psShifrAndNum As String
Public psName As String

Attribute VB_Name = "BrowseDialog"
Option Explicit
'----------------------------------------------------------------------
' 64 bit VBA 7 version of File and Folder Browswers
' FileBrowseOpen()
' FileBrowseSave()
' FolderBrowse()
' Much of the original 32 bit module was donated by the good people of XtremeVbTalk.com
' I massaged it to be 64 bit with VBA 7 code lifted from numerous sites on the web
'----------------------------------------------------------------------

Private Declare PtrSafe Function GetOpenFileName Lib "comdlg32.dll" Alias _
"GetOpenFileNameA" (pOpenfilename As OPENFILENAME) As Long

Private Declare PtrSafe Function GetSaveFileName Lib "comdlg32.dll" Alias _
"GetSaveFileNameA" (pOpenfilename As OPENFILENAME) As Long

Private Declare PtrSafe Function SHBrowseForFolder Lib "shell32.dll" _
Alias "SHBrowseForFolderA" (lpBrowseInfo As BrowseInfo) As Long

Private Declare PtrSafe Function SHGetPathFromIDList Lib "shell32.dll" _
(ByVal pidList As LongPtr, ByVal lpBuffer As String) As Long


Public Declare PtrSafe Function SendMessageA Lib "user32" _
(ByVal Hwnd As LongPtr, ByVal wMsg As Long, _
ByVal wParam As LongPtr, lParam As Any) As LongPtr

Private Declare PtrSafe Sub CoTaskMemFree Lib "ole32.dll" (ByVal hMem As LongPtr)

Private Const BIF_RETURNONLYFSDIRS As Long = 1
Private Const CSIDL_DRIVES As Long = &H11
Private Const WM_USER As Long = &H400
Private Const MAX_PATH As Long = 260
'// message from browser
Private Const BFFM_INITIALIZED As Long = 1
Private Const BFFM_SELCHANGED As Long = 2
Private Const BFFM_VALIDATEFAILEDA As Long = 3 '// lParam:szPath ret:1(cont),0(EndDialog)
Private Const BFFM_VALIDATEFAILEDW As Long = 4 '// lParam:wzPath ret:1(cont),0(EndDialog)
Private Const BFFM_IUNKNOWN As Long = 5 '// provides IUnknown to client. lParam: IUnknown*
'// messages to browser
Private Const BFFM_SETSTATUSTEXTA As Long = WM_USER + 100
Private Const BFFM_ENABLEOK As Long = WM_USER + 101
Private Const BFFM_SETSELECTIONA As Long = WM_USER + 102
Private Const BFFM_SETSELECTIONW As Long = WM_USER + 103
Private Const BFFM_SETSTATUSTEXTW As Long = WM_USER + 104
Private Const BFFM_SETOKTEXT As Long = WM_USER + 105 '// Unicode only
Private Const BFFM_SETEXPANDED As Long = WM_USER + 106 '// Unicode only


Private Type OPENFILENAME
lStructSize As Long
hWndOwner As LongPtr
hInstance As LongPtr
lpstrFilter As String
lpstrCustomFilter As String
nMaxCustFilter As Long
nFilterIndex As Long
lpstrFile As String
nMaxFile As Long
lpstrFileTitle As String
nMaxFileTitle As Long
lpstrInitialDir As String
lpstrTitle As String
flags As Long
nFileOffset As Integer
nFileExtension As Integer
lpstrDefExt As String
lCustData As Long
lpfnHook As LongPtr
lpTemplateName As String
End Type
Public Type BrowseInfo
hWndOwner As LongPtr
pIDLRoot As LongPtr
pszDisplayName As String
lpszTitle As String
ulFlags As Long
lpfnCallback As LongPtr
lParam As LongPtr
iImage As Long
End Type
 
'====== File Browsers for 64 bit VBA 7 ========
Public Function FileBrowseOpen(ByVal sInitFolder As String, _
ByVal sTitle As String, _
ByVal sFilter As String, _
ByVal nFilterIndex As Integer) As String


Dim OpenFile As OPENFILENAME
Dim lReturn As Long

sInitFolder = CorrectPath(sInitFolder)


OpenFile.lpstrInitialDir = sInitFolder

' Swap filter separator for api separator
sFilter = Replace(sFilter, "|", Chr(0))



OpenFile.lpstrFilter = sFilter
OpenFile.nFilterIndex = nFilterIndex
OpenFile.lpstrTitle = sTitle


OpenFile.hWndOwner = 0
OpenFile.lpstrFile = String(257, 0)
OpenFile.nMaxFile = LenB(OpenFile.lpstrFile) - 1
OpenFile.lStructSize = LenB(OpenFile)

OpenFile.lpstrFileTitle = OpenFile.lpstrFile
OpenFile.nMaxFileTitle = OpenFile.nMaxFile

OpenFile.flags = 0

lReturn = GetOpenFileName(OpenFile)

If lReturn = 0 Then
FileBrowseOpen = ""
Else
FileBrowseOpen = Trim(Left(OpenFile.lpstrFile, InStr(1, OpenFile.lpstrFile, vbNullChar) - 1))
End If
End Function
Public Function FileBrowseSave(ByVal sDefaultFilename As String, _
ByVal sInitFolder As String, _
ByVal sTitle As String, _
ByVal sFilter As String, _
ByVal nFilterIndex As Integer) As String
Dim PadCount As Integer
Dim OpenFile As OPENFILENAME
Dim lReturn As Long

sInitFolder = CorrectPath(sInitFolder)

' Swap filter separator for api separator
sFilter = Replace(sFilter, "|", Chr(0))

OpenFile.lpstrFilter = sFilter
OpenFile.nFilterIndex = 1
OpenFile.hWndOwner = 0

PadCount = 260 - Len(sDefaultFilename)
OpenFile.lpstrFile = sDefaultFilename & String(PadCount, Chr(0))
'OpenFile.lpstrFile = String(257, 0)
OpenFile.nMaxFile = LenB(OpenFile.lpstrFile) - 1
OpenFile.lStructSize = LenB(OpenFile)

OpenFile.lpstrFileTitle = OpenFile.lpstrFile
OpenFile.nMaxFileTitle = OpenFile.nMaxFile
OpenFile.lpstrInitialDir = sInitFolder
OpenFile.lpstrTitle = sTitle
OpenFile.flags = 0
lReturn = GetSaveFileName(OpenFile)

If lReturn = 0 Then
FileBrowseSave = ""
Else
FileBrowseSave = Trim(Left(OpenFile.lpstrFile, InStr(1, OpenFile.lpstrFile, vbNullChar) - 1))
End If
End Function
 

'====== Folder Browser for 64 bit VBA 7 ========
Public Function FolderBrowse(ByVal sDialogTitle As String, ByVal sInitFolder As String) As String
Dim ReturnPath As String

Dim b(MAX_PATH) As Byte
Dim pItem As Long
Dim sFullPath As String
Dim bi As BrowseInfo
Dim ppidl As Long

sInitFolder = CorrectPath(sInitFolder)

' Note VBA windows and dialogs do not have an hWnd property.
bi.hWndOwner = 0 'Windows Main Screen handle.

' SHGetSpecialFolderLocation bi.hWndOwner, CSIDL_DRIVES, ppidl

bi.pIDLRoot = 0 'ppidl


bi.pszDisplayName = VarPtr(b(0))
bi.lpszTitle = sDialogTitle
bi.ulFlags = BIF_RETURNONLYFSDIRS
If FolderExists(sInitFolder) Then bi.lpfnCallback = PtrToFunction(AddressOf BFFCallback)
bi.lParam = StrPtr(sInitFolder)
pItem = SHBrowseForFolder(bi)

If pItem Then ' Succeeded
sFullPath = Space$(MAX_PATH)
If SHGetPathFromIDList(pItem, sFullPath) Then
ReturnPath = Left$(sFullPath, InStr(sFullPath, vbNullChar) - 1) ' Strip nulls
CoTaskMemFree pItem
End If
End If

If ReturnPath <> "" Then
If Right$(ReturnPath, 1) <> "\" Then
ReturnPath = ReturnPath & "\"
End If
End If

FolderBrowse = ReturnPath

End Function
' typedef int (CALLBACK* BFFCALLBACK)(HWND hwnd, UINT uMsg, LPARAM lParam, LPARAM lpData);
Private Function BFFCallback(ByVal Hwnd As LongPtr, ByVal uMsg As LongPtr, ByVal lParam As LongPtr, ByVal sData As String) As LongPtr
If uMsg = BFFM_INITIALIZED Then
SendMessageA Hwnd, BFFM_SETSELECTIONA, True, ByVal sData
End If
End Function
Private Function PtrToFunction(ByVal lFcnPtr As LongPtr) As LongPtr
PtrToFunction = lFcnPtr
End Function
Private Function CorrectPath(ByVal sPath As String) As String
If Right$(sPath, 1) = "\" Then
If Len(sPath) > 3 Then sPath = Left$(sPath, Len(sPath) - 1) ' Strip backslash from non-root
Else
If Len(sPath) = 2 Then sPath = sPath & "\" ' Append backslash to root
End If
CorrectPath = sPath
End Function

Public Function FolderExists(ByVal sFolderName As String) As Boolean
Dim att As Long
On Error Resume Next
att = GetAttr(sFolderName)
If Err.Number = 0 Then
FolderExists = True
Else
Err.Clear
FolderExists = False
End If
On Error GoTo 0
End Function

Attribute VB_Name = "BrowseFolder"
'Option Explicit
'
'Declare PtrSafe Function GetDC Lib "user32" (ByVal Hwnd As Long) As Long
'Declare PtrSafe Function ReleaseDC Lib "user32" (ByVal Hwnd As Long, _
'  ByVal hDC As Long) As Long
'Declare PtrSafe Function GetDeviceCaps Lib "gdi32" (ByVal hDC As Long, _
'  ByVal nIndex As Long) As Long
'
'Const HWND_DESKTOP As Long = 0
'Const LOGPIXELSX As Long = 88
'Const LOGPIXELSY As Long = 90
'Const HORZRES As Long = 8
'Const VERTRES As Long = 10
'
'
'Public Type RECT
'    Left As Long
'    Top As Long
'    Right As Long
'    Bottom As Long
'End Type
'
'Public Declare PtrSafe Function MoveWindow Lib "user32.dll" ( _
'     ByVal Hwnd As Long, _
'     ByVal X As Long, _
'     ByVal y As Long, _
'     ByVal nWidth As Long, _
'     ByVal nHeight As Long, _
'     ByVal bRepaint As Long) As Long
'
'Public Declare PtrSafe Function GetWindowRect Lib "user32.dll" ( _
'     ByVal Hwnd As Long, _
'     lpRect As RECT) As Long
'
'Public Declare PtrSafe Function WaitForInputIdle Lib "user32" ( _
'    ByVal hProcess As Long, _
'    ByVal dwMilliseconds As Long) As Long
'
'Public Declare PtrSafe Function FindWindowEx Lib "user32.dll" Alias "FindWindowExA" ( _
'     ByVal hWnd1 As Long, _
'     ByVal hWnd2 As Long, _
'     ByVal lpsz1 As String, _
'     ByVal lpsz2 As String) As Long
'
'Public Declare PtrSafe Function EnumThreadWindows Lib "user32" _
'    (ByVal dwThreadId As Long, _
'    ByVal lpfn As Long, _
'    ByVal lParam As Long) As Long
'
'Public Declare PtrSafe Function GetWindowThreadProcessId Lib "user32.dll" ( _
'     ByVal Hwnd As Long, _
'     lpdwProcessId As Long) As Long
'
'Public Declare PtrSafe Function SetWindowPos Lib "user32.dll" ( _
'     ByVal Hwnd As Long, _
'     ByVal hWndInsertAfter As Long, _
'     ByVal X As Long, _
'     ByVal y As Long, _
'     ByVal cx As Long, _
'     ByVal cy As Long, _
'     ByVal wFlags As Long) As Long
'
'Public Declare PtrSafe Function SetWindowText Lib "user32.dll" Alias "SetWindowTextA" ( _
'     ByVal Hwnd As Long, _
'     ByVal lpString As String) As Long
'
'Public Const SWP_SHOWWINDOW = &H40
'Public Const HWND_TOPMOST = -1
'
'Public g_CurrentDirectory As String
'Public g_FileMasks() As String
'Public g_ChangeSize As Boolean
'Public g_DialogTitle As String
'Public g_RatioX As Double, g_RatioY As Double
'Public g_CenterOnScreen As Boolean
'Public g_TopMost As Boolean
'
'Public g_newLeft As Long, g_newTop As Long
'Public g_deltaH As Long, g_deltaW As Long
'
'Public Const WM_USER As Long = &H400
'Public Const BFFM_INITIALIZED = 1
'Public Const BFFM_SELCHANGED = 2
'Public Const BFFM_SETSTATUSTEXT = (WM_USER + 100)
'Public Const BFFM_ENABLEOK = (WM_USER + 101)
'Public Const BFFM_SETSELECTION = (WM_USER + 102)
'
'Public Type BrowseInfo
'    hWndOwner As Long
'    pIDLRoot As Long
'    pszDisplayName As Long
'    lpszTitle As Long
'    ulFlags As Long
'    lpfnCallback As Long
'    lParam As Long
'    iImage As Long
'End Type
'
'Public Enum WhatBrowse
'    BIF_RETURNONLYFSDIRS = &H1
'    BIF_BROWSEINCLUDEFILES = &H1 Or &H4000
'    BIF_BROWSEFORCOMPUTER = &H1000
'    BIF_BROWSEFORPRINTER = &H2000
'    BIF_DONTGOBELOWDOMAIN = &H2
'    BIF_STATUSTEXT = &H4
'    BIF_NEWDIALOGSTYLE = &H40
'    BIF_EDITBOX = &H10
'    BIF_USENEWUI = (BIF_NEWDIALOGSTYLE Or BIF_EDITBOX)
'    BIF_RETURNFSANCESTORS = &H8
'End Enum
'
'Public Const MAX_PATH = 260&
'Public Declare PtrSafe Function SendMessage Lib "user32" Alias "SendMessageA" _
'  (ByVal Hwnd As Long, _
'   ByVal wMsg As Long, _
'   ByVal wParam As Long, _
'   lParam As Any) As Long
'Public Declare PtrSafe Sub CoTaskMemFree Lib "ole32.dll" (ByVal hMem As Long)
'Public Declare PtrSafe Function lstrcat Lib "kernel32" Alias "lstrcatA" _
'    (ByVal lpString1 As String, _
'    ByVal lpString2 As String) As Long
'Public Declare PtrSafe Function SHBrowseForFolder Lib "shell32" (lpbi As BrowseInfo) As Long
'Public Declare PtrSafe Function SHGetPathFromIDList Lib "shell32" _
'    (ByVal pidList As Long, _
'    ByVal lpBuffer As String) As Long
'
'Public Function fBrowseForFolder(ByVal hWnd_Owner As Long, _
'                                 ByVal sPrompt As String, _
'                                 ByVal WhatBr As Long, _
'                                 ByVal DialogTitle As String, _
'                                 Optional ByVal initDir As String = "", _
'                                 Optional ByRef fileMasks As String = "", _
'                                 Optional ByVal ChangeSize As Boolean = False, _
'                                 Optional ByVal RatioX As Double = 1, _
'                                 Optional ByVal RatioY As Double = 1, _
'                                 Optional ByVal CenterOnScreen As Boolean = False, _
'                                 Optional ByVal PromptColor As Long = 0&, _
'                                 Optional ByVal PathColor As Long = 0&, _
'                                 Optional ByVal TopMost As Boolean) As String
'
'    Dim iNull As Integer
'    Dim lpIDList As Long
'    Dim lResult As Long
'    Dim sPath As String
'    Dim udtBI As BrowseInfo
'
'    g_DialogTitle = DialogTitle
'    g_ChangeSize = ChangeSize
'    g_RatioX = RatioX
'    g_RatioY = RatioY
'    g_CenterOnScreen = CenterOnScreen
'    g_TopMost = TopMost
'
'    If initDir = "" Then
'        g_CurrentDirectory = ""
'    Else
'        g_CurrentDirectory = initDir & vbNullChar
'    End If
'
'    If fileMasks = "" Then
'        ReDim g_FileMasks(0 To 0)
'        g_FileMasks(0) = ""
'    Else
'        g_FileMasks = Split(fileMasks, "|")
'    End If
'
'    With udtBI
'        .hWndOwner = hWnd_Owner
'        .lpszTitle = lstrcat(sPrompt, "")
'        .ulFlags = WhatBr
'        .lpfnCallback = GetAddressofFunction(AddressOf BrowseCallbackProc)  'get address of function.
'    End With
'    lpIDList = SHBrowseForFolder(udtBI)
'
'    If lpIDList Then
'        sPath = String$(MAX_PATH, 0)
'        lResult = SHGetPathFromIDList(lpIDList, sPath)
'        Call CoTaskMemFree(lpIDList)
'        iNull = InStr(sPath, vbNullChar)
'        If iNull Then sPath = Left$(sPath, iNull - 1)
'    End If
'    fBrowseForFolder = sPath
'
'End Function
'
'Public Function BrowseCallbackProc(ByVal Hwnd As Long, ByVal uMsg As Long, ByVal lp As Long, ByVal pData As Long) As Long
'
'    Dim lpIDList As Long
'    Dim ret As Long
'    Dim sBuffer As String
'    Dim i As Integer, flag As Boolean, sPath As String
'
'    On Error Resume Next
'
'    Select Case uMsg
'
'        Case BFFM_INITIALIZED
'            If g_CurrentDirectory <> "" Then
'                Call SendMessage(Hwnd, BFFM_SETSELECTION, 1, ByVal g_CurrentDirectory)
'            End If
'
'            SetWindowText Hwnd, g_DialogTitle
'            If g_ChangeSize Then
'                Call ResizeDialog(Hwnd)
'
'            Else
'                If g_CenterOnScreen Then Call CenterDialog(Hwnd)
'            End If
'
'        Case BFFM_SELCHANGED
'            sBuffer = Space$(MAX_PATH)
'
'            ret = SHGetPathFromIDList(lp, sBuffer)
'            If ret = 1 Then
'                Call SendMessage(Hwnd, BFFM_SETSTATUSTEXT, 0, ByVal sBuffer)
'                If g_FileMasks(0) <> "" Then
'                    sPath = Left$(sBuffer, InStr(1, sBuffer, vbNullChar) - 1)
'                    If Right$(sPath, 1) <> "\" Then sPath = sPath + "\"
'                    flag = False
'                    For i = 0 To UBound(g_FileMasks)
'                        If Dir(sPath + g_FileMasks(i)) <> "" Then flag = True
'                    Next i
'                    If flag Then
'                        Call SendMessage(Hwnd, BFFM_ENABLEOK, 0, ByVal 1&)
'                    Else
'                        Call SendMessage(Hwnd, BFFM_ENABLEOK, 0, ByVal 0&)
'                    End If
'                End If
'            End If
'
'        Case Else
'    End Select
'
'    BrowseCallbackProc = 0
'
'End Function
'
'Public Function GetAddressofFunction(add As Long) As Long
'    GetAddressofFunction = add
'End Function
'
'Private Sub ResizeDialog(ByVal Hwnd As Long)
'    Dim pid As Long, thread_id As Long
'    Dim screenWidth As Long, screenHeight As Long
'    Dim winWidth As Long, winHeight As Long
'    Dim R As RECT
'    Dim lngDC As Long
'    Dim lWidth As Long
'    Dim lHeight As Long
'
'    lngDC = GetDC(HWND_DESKTOP)
'    screenWidth = GetDeviceCaps(lngDC, HORZRES)
'    screenHeight = GetDeviceCaps(lngDC, VERTRES)
'
'    GetWindowRect Hwnd, R
'
'    winWidth = (R.Right - R.Left) * g_RatioX
'    winHeight = (R.Bottom - R.Top) * g_RatioY
'    g_deltaH = winHeight - (R.Bottom - R.Top)
'    g_deltaW = winWidth - (R.Right - R.Left)
'
'    If g_CenterOnScreen Then
'        g_newLeft = (screenWidth - winWidth) / 2
'        g_newTop = (screenHeight - winHeight) / 2
'    Else
'        g_newLeft = R.Left
'        g_newTop = R.Top
'    End If
'
'    If g_TopMost Then
'        SetWindowPos Hwnd, HWND_TOPMOST, g_newLeft, g_newTop, winWidth, winHeight, SWP_SHOWWINDOW
'    Else
'        SetWindowPos Hwnd, 0, g_newLeft, g_newTop, winWidth, winHeight, SWP_SHOWWINDOW
'    End If
'
'    thread_id = GetWindowThreadProcessId(Hwnd, pid)
'    Call WaitForInputIdle(pid, 1000&)
'    EnumThreadWindows thread_id, AddressOf EnumThreadWndProc, 0&
'
'End Sub
'
''--------------------------------------------------
'Function TwipsPerPixelX() As Single
''--------------------------------------------------
''Returns the width of a pixel, in twips.
''--------------------------------------------------
'  Dim lngDC As Long
'  lngDC = GetDC(HWND_DESKTOP)
'  TwipsPerPixelX = 1440& / GetDeviceCaps(lngDC, LOGPIXELSX)
'  ReleaseDC HWND_DESKTOP, lngDC
'End Function
'
''--------------------------------------------------
'Function TwipsPerPixelY() As Single
''--------------------------------------------------
''Returns the height of a pixel, in twips.
''--------------------------------------------------
'  Dim lngDC As Long
'  lngDC = GetDC(HWND_DESKTOP)
'  TwipsPerPixelY = 1440& / GetDeviceCaps(lngDC, LOGPIXELSY)
'  ReleaseDC HWND_DESKTOP, lngDC
'End Function
'
'Public Function EnumThreadWndProc(ByVal Hwnd As Long, ByVal lParam As Long) As Long
'    Dim treeHwnd As Long, okButtonHwnd As Long, cancelButtonHwnd As Long, promptHwnd As Long, folderHwnd As Long
'    Dim R As RECT
'    Static allControlsAdjusted As Integer
'
'    okButtonHwnd = FindWindowEx(Hwnd, ByVal 0&, "Button", vbNullString)
'    If okButtonHwnd <> 0 Then
'        GetWindowRect okButtonHwnd, R
'        MoveWindow okButtonHwnd, (R.Left - g_newLeft - 3) + g_deltaW, (R.Top - g_newTop - 22) + g_deltaH, R.Right - R.Left, R.Bottom - R.Top, 1
'        allControlsAdjusted = allControlsAdjusted + 10000
'        cancelButtonHwnd = FindWindowEx(Hwnd, okButtonHwnd, "Button", vbNullString)
'        If cancelButtonHwnd <> 0 Then
'            GetWindowRect cancelButtonHwnd, R
'            MoveWindow cancelButtonHwnd, (R.Left - g_newLeft - 3) + g_deltaW, (R.Top - g_newTop - 22) + g_deltaH, R.Right - R.Left, R.Bottom - R.Top, 1
'            allControlsAdjusted = allControlsAdjusted + 1000
'        End If
'    End If
'
'    treeHwnd = FindWindowEx(Hwnd, ByVal 0&, "SysTreeView32", vbNullString)
'    If treeHwnd <> 0 Then
'        GetWindowRect treeHwnd, R
'        MoveWindow treeHwnd, R.Left - g_newLeft - 3, R.Top - g_newTop - 22, (R.Right - R.Left) + g_deltaW, (R.Bottom - R.Top) + g_deltaH, 1
'        allControlsAdjusted = allControlsAdjusted + 100
'    End If
'
'    promptHwnd = FindWindowEx(Hwnd, ByVal 0&, "Static", vbNullString)
'    If promptHwnd <> 0 Then
'        GetWindowRect promptHwnd, R
'        MoveWindow promptHwnd, R.Left - g_newLeft - 3, R.Top - g_newTop - 22, (R.Right - R.Left) + g_deltaW, R.Bottom - R.Top, 1
'        allControlsAdjusted = allControlsAdjusted + 10
'        folderHwnd = FindWindowEx(Hwnd, promptHwnd, "Static", vbNullString)
'        If folderHwnd <> 0 Then
'            GetWindowRect folderHwnd, R
'            MoveWindow folderHwnd, R.Left - g_newLeft - 3, R.Top - g_newTop - 22, (R.Right - R.Left) + g_deltaW, R.Bottom - R.Top, 1
'            allControlsAdjusted = allControlsAdjusted + 1
'        End If
'    End If
'
'    EnumThreadWndProc = Not (allControlsAdjusted = 11111)
'End Function
'
'Private Sub CenterDialog(ByVal Hwnd As Long)
'    Dim screenWidth As Long, screenHeight As Long
'    Dim winWidth As Long, winHeight As Long
'    Dim R As RECT
'    Dim lngDC As Long
'    Dim lWidth As Long
'    Dim lHeight As Long
'
'    lngDC = GetDC(HWND_DESKTOP)
'    screenWidth = GetDeviceCaps(lngDC, HORZRES)
'    screenHeight = GetDeviceCaps(lngDC, VERTRES)
'
'    GetWindowRect Hwnd, R
'
'    winWidth = (R.Right - R.Left)
'    winHeight = (R.Bottom - R.Top)
'
'    g_newLeft = (screenWidth - winWidth) / 2
'    g_newTop = (screenHeight - winHeight) / 2
'
'    SetWindowPos Hwnd, 0, g_newLeft, g_newTop, winWidth, winHeight, SWP_SHOWWINDOW
'End Sub
'
'
'Public Sub Тест_выбор_папки()
'
'   Dim st As String
'   Dim lngDC As Long
'
'   lngDC = GetDC(HWND_DESKTOP)
'
'    st = fBrowseForFolder(0&, _
'                          "Внимание: вложенные папки не учиываются." & vbCrLf & _
'                                    "Поэтому выбирайте каждый каталог по отдельности." & vbCrLf & _
'                                    "Можно выбрать только папку содержащую файлы dwg!", _
'                          BIF_RETURNONLYFSDIRS, _
'                          "Выберите папку c блоками", _
'                          "\\Sgpsrv2\спд\Конструкторы\Пан. Кронверк( 17 эт.)\От архитекторов 2.10.08", _
'                          "*.DWG*", _
'                          True, _
'                          1, _
'                          1, _
'                          True, _
'                          0, _
'                          0, _
'                          True)
'    If Len(st) > 0 Then MsgBox "Вы выбрали папку:" + vbCr + st, vbInformation, "Информация"
'
'End Sub

Attribute VB_Name = "ClassINI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
 
Private strInI As String
 
'// Win API Declares
Private Declare PtrSafe Function WritePrivateProfileString _
  Lib "kernel32" Alias "WritePrivateProfileStringA" _
 (ByVal lpApplicationName As String, _
  ByVal lpKeyName As Any, _
  ByVal lpString As Any, _
  ByVal lpFileName As String) As Long
 
Private Declare PtrSafe Function GetPrivateProfileString _
  Lib "kernel32" Alias "GetPrivateProfileStringA" _
 (ByVal lpApplicationName As String, _
  ByVal lpKeyName As Any, _
  ByVal lpDefault As String, _
  ByVal lpReturnedString As String, _
  ByVal nSize As Long, _
  ByVal lpFileName As String) As Long
 
Private Function MakePath(ByVal strFileName As String, _
  ByVal strPath As String) As String
 
 '// Makes an INI file: Guarantees a sub dir
 Do While Right$(strPath, 1) = "\"
   strPath = Left$(strPath, Len(strPath) - 1)
 Loop
 
 Do While Left$(strFileName, 1) = "\"
   strFileName = Mid$(strFileName, 2)
 Loop
 
 '// Return the path
 MakePath = strPath & "\" & strFileName
End Function
 
Public Sub CreateIni(strFileName As String, strPath As String)
 '// Make a new ini file
 strInI = MakePath(strFileName, strPath)
End Sub
 
Public Sub WriteFile(strSection As String, _
 strKey As String, _
 strValue As String)
 
 '// Write to strINI
 WritePrivateProfileString strSection, _
   strKey, strValue, strInI
End Sub
 
Public Function GetFile(strSection As String, _
  strKey As String) As String
 
  Dim strTmp As String
  Dim lngRet As String
 
  strTmp = String$(100, 0)
  lngRet = GetPrivateProfileString(strSection, _
    strKey, "", strTmp, _
    Len(strTmp), strInI)
 
  GetFile = StrZ(strTmp)
 
End Function
 
Public Property Let INIFile(ByVal New_IniPath As String)
   'Устанавливаем путь к файлу ini
   strInI = New_IniPath
End Property
Public Property Get INIFile() As String
   INIFile = strInI
End Property
 
 
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "FormAlbum"
Attribute VB_Base = "0{5FD7ED39-53AE-41C7-820B-21157CECAFEE}{06700DB9-2C94-40FC-B22F-D0E8F6B1B6AB}"
Attribute VB_GlobalNameSpace = False
Attribute VB_Creatable = False
Attribute VB_PredeclaredId = True
Attribute VB_Exposed = False
Attribute VB_TemplateDerived = False
Attribute VB_Customizable = False
Option Explicit

Private Sub cmbExit_Click()
  TextBoxShifr = ""
  Hide
End Sub

Private Sub cmbOK_Click()
  Hide
End Sub

Private Sub ComboBox1_Exit(ByVal Cancel As MSForms.ReturnBoolean)
  'добавляем запись
  Dim i As Integer
  
  If ComboBox1.Text = "" Then Exit Sub
  
  For i = 0 To ComboBox1.ListCount - 1
    If LCase(ComboBox1.Text) = LCase(ComboBox1.List(i)) Then
      ComboBox1.List(i) = ComboBox1.Text
      Exit Sub
    End If
  Next
    ComboBox1.AddItem ComboBox1.Text
End Sub

Private Sub UserForm_Activate()
  If TextBoxShifrAlbum = "" Then
    TextBoxShifrAlbum = "Альбом 1"
  End If
End Sub

Attribute VB_Name = "FormMain"
Attribute VB_Base = "0{F78CCC06-2AA5-4BC6-92E3-EB4F51995970}{6C09991E-B719-4B88-A168-2EEC8935CF7F}"
Attribute VB_GlobalNameSpace = False
Attribute VB_Creatable = False
Attribute VB_PredeclaredId = True
Attribute VB_Exposed = False
Attribute VB_TemplateDerived = False
Attribute VB_Customizable = False
Option Explicit

Private Sub cmbAddAlbum_Click()
  'в выбранный шифр жби добавляем имя альбома
  
  Dim oShifr As ShifrAndAlbums
  Dim oAlbum As Album
  Dim sNewAlbum As String
  Dim index As Integer
  
  index = ListBoxShifrs.ListIndex
  If index = -1 Then
    MsgBox "Не выбран шифр", vbCritical, pcsVBProjectName
    Exit Sub
  End If
  
  Set oShifr = pcolShifrs(ListBoxShifrs.Text)
  
  FormAlbum.TextBoxShifr = oShifr.psShifrGBI
  FormAlbum.Show
  If FormAlbum.TextBoxShifr = "" Then Exit Sub
  If FormAlbum.ComboBox1.Text = "" Then
    Exit Sub
  End If
  
  'добавляем альбом в коллекцию шифров
  Set oAlbum = New Album
  oAlbum.psName = FormAlbum.ComboBox1.Text
  oAlbum.psShifrAndNum = FormAlbum.TextBoxShifrAlbum
  On Error Resume Next
  oShifr.pcolAlbums.add oAlbum, oAlbum.psName
  If Err Then
    Err.Clear
    MsgBox "Такой альбом уже есть", vbCritical, pcsVBProjectName
    Exit Sub
  End If
  
  'добавляем в листбокс
  ListBoxShifrAlbums.AddItem oAlbum.psShifrAndNum, 0
  ListBoxShifrAlbums.List(0, 1) = oAlbum.psName
  
End Sub

Private Sub cmbBrowse_Click()
  
  Dim strBrowseFolder As String
  Dim strPathDefault As String
  
  'Очищаем листбоксы
  ListBoxFilesMS.Clear
  ListBoxListAlbums.Clear
  ListBoxShifrAlbums.Clear
  ListBoxShifrs.Clear
  
  'путь по умолчанию
'  If ThisDrawing.FullName = "" Then
    strPathDefault = psMontagkyFolderPath
'  Else
'    strPathDefault = ThisDrawing.Path
'  End If
  
  'открываем диалог выбора папок
  strBrowseFolder = BrowseDialog.FolderBrowse("Выбор папки c монтажками", strPathDefault)
    'strBrowseFolder = BrowseFolder.fBrowseForFolder(hWnd_Owner:=0&, _
                          sPrompt:="", _
                          WhatBr:=BIF_RETURNONLYFSDIRS Or BIF_STATUSTEXT, _
                          DialogTitle:="Выбор папки c монтажками", _
                          initDir:=strPathDefault, _
                          fileMasks:="*.DWG*", _
                          ChangeSize:=True, _
                          RatioX:=1, _
                          RatioY:=1, _
                          CenterOnScreen:=True, _
                          TopMost:=True)
    'fileMasks:="*.DWG|*.TIF" - пример для фильтра типов файлов
   If Len(strBrowseFolder) = 0 Then 'если не выбрана папка
      Exit Sub
   End If
   
   RemoveSlashAtEndOfPathFolder strBrowseFolder
   
   TBMontagkyFolderPath = strBrowseFolder
   psMontagkyFolderPath = strBrowseFolder
    
    'вывод списка файлов монтажек
    Functions.GetListFileMontagek
    
End Sub

Private Sub cmbDelAlbum_Click()
  'из выбранного шифра жби удаляем имя альбома
  
  Dim oShifr As ShifrAndAlbums
  Dim sNewAlbum As String
  Dim indexShifr As Integer
  Dim indexAlbum As Integer
  
  indexShifr = ListBoxShifrs.ListIndex
  If indexShifr = -1 Then
    MsgBox "Не выбран шифр", vbCritical, pcsVBProjectName
    Exit Sub
  End If
  
  indexAlbum = ListBoxShifrAlbums.ListIndex
  If indexAlbum = -1 Then
    MsgBox "Не выбран альбом", vbCritical, pcsVBProjectName
    Exit Sub
  End If
  
  'удаляем из листбокс
  ListBoxShifrAlbums.RemoveItem indexAlbum
  
  Set oShifr = pcolShifrs(ListBoxShifrs.Text)
  
  'удаляем альбом из коллекции шифров
  On Error Resume Next
  oShifr.pcolAlbums.Remove indexShifr
  
End Sub

Private Sub cmbEditAlbum_Click()
  'изменяем имя выбранного альбома
  
  Dim oShifr As ShifrAndAlbums
  Dim oAlbum As Album
  Dim sNewAlbum As String
  Dim indexShifr As Integer
  Dim indexAlbum As Integer
  
  indexShifr = ListBoxShifrs.ListIndex
  If indexShifr = -1 Then
    MsgBox "Не выбран шифр", vbCritical, pcsVBProjectName
    Exit Sub
  End If
  indexAlbum = ListBoxShifrAlbums.ListIndex
  If indexAlbum = -1 Then
    MsgBox "Не выбран альбом", vbCritical, pcsVBProjectName
    Exit Sub
  End If
  
  Set oShifr = pcolShifrs(ListBoxShifrs)
  FormAlbum.TextBoxShifr = oShifr.psShifrGBI
  FormAlbum.Show
  If FormAlbum.TextBoxShifr = "" Then Exit Sub
  If FormAlbum.TextBoxShifrAlbum = "" Or FormAlbum.ComboBox1.Text = "" Then
    Exit Sub
  End If
  
  'изменяем имя альбома в коллекции
  Set oAlbum = oShifr.pcolAlbums(ListBoxShifrAlbums)
  oAlbum.psName = FormAlbum.ComboBox1.Text
  oAlbum.psShifrAndNum = FormAlbum.TextBoxShifrAlbum
  
  'в листбоксе
  ListBoxShifrAlbums.List(indexAlbum, 0) = oAlbum.psShifrAndNum
  ListBoxShifrAlbums.List(indexAlbum, 1) = oAlbum.psName
  
End Sub

Private Sub cmbExit_Click()
  'сохраненние параметров в ини
  Functions.SaveToIni
  End
End Sub

Private Sub cmbHide_Click()
  Hide
End Sub

Private Sub cmbInsTable_Click()
  'заполнение таблицы и вставка
  
  Dim objTable As AcadTable
  Dim vPtTable As Variant
  Dim intRow As Integer
  Dim oShifr As ShifrAndAlbums
  Dim colShifrsOutAlbums As New Collection
  Dim sShifr As String
  Dim iVal As Integer
  Dim i As Integer
  Dim col As New AcadAcCmColor
  
  'проверяем шифры без альбомов, но с ".И" в имени
  For i = 0 To ListBoxShifrs.ListCount - 1
    sShifr = ListBoxShifrs.List(i)
    
    ' Изм.07.04.2011. Включать все обозначения, а не только "наши".
    'iVal = VBA.InStr(1, sShifr, ".И", vbTextCompare)
    'If iVal > 0 Then
      'значит это наш шифр, проверяем альбом
      Set oShifr = pcolShifrs(sShifr)
      If oShifr.pcolAlbums.Count = 0 Then
        'нет альбомов в этом шифре, добавляем в массив строк наших шифров без альбомов
        colShifrsOutAlbums.add sShifr
      End If
    'End If
  Next
  
  Functions.MakeTableStyleForSpec "Спецификация"
  
  FormMain.Hide
  
  ThisDrawing.ActiveLayer.LayerOn = True
      ThisDrawing.ActiveLayer.Lock = False
      'запрашиваем точку вставки таблы
      vPtTable = ThisDrawing.Utility.GetPoint(, "Верхний левый угол таблицы")
      Set objTable = ThisDrawing.ModelSpace.AddTable(vPtTable, 3, 3, 8, 40)
      objTable.StyleName = "Спецификация"
      objTable.RegenerateTableSuppressed = True
      objTable.SetRowHeight 0, 10
      objTable.SetCellValue 0, 0, "Ведомость ссылочных и прилагаемых документов"
      objTable.SetRowHeight 1, 15
      objTable.SetRowHeight 2, 8
      objTable.SetCellValue 1, 0, "Обозначение"
      objTable.SetColumnWidth 0, 60
      objTable.SetCellValue 1, 1, "Наименование"
      objTable.SetColumnWidth 1, 95
      objTable.SetCellValue 1, 2, "Примечание"
      objTable.SetColumnWidth 2, 30
            
      objTable.SetText 2, 1, "\LСсылочные документы"
      objTable.SetCellAlignment 2, 1, acMiddleCenter
      objTable.InsertRows 3, 8, 1
      
      intRow = 3
      For i = 0 To ListBoxListAlbums.ListCount - 1
         'заполняем таблицу
         objTable.SetText intRow, 0, ListBoxListAlbums.List(i, 0)
         objTable.SetText intRow, 1, ListBoxListAlbums.List(i, 1)
         intRow = intRow + 1
         objTable.InsertRows intRow, 8, 1
      Next
      
      'проверяем есть ли наши шифры без альбомов
      If colShifrsOutAlbums.Count <> 0 Then
        intRow = intRow + 1
        objTable.InsertRows intRow, 8, 1
        col.SetRGB 100, 200, 50
        For i = 0 To colShifrsOutAlbums.Count - 1
          sShifr = colShifrsOutAlbums(i + 1)
          objTable.SetText intRow, 0, colShifrsOutAlbums(i + 1)
          'цвет текста изменить
          objTable.SetCellContentColor intRow, 0, col
          objTable.SetText intRow, 1, "нет альбомов!!!"
          'цвет текста изменить
          objTable.SetCellContentColor intRow, 1, col
          intRow = intRow + 1
          objTable.InsertRows intRow, 8, 1
        Next
      End If
      
      'objTable.ScaleEntity vPtTable, CDbl(FormaPoShifru.TextBoxM)
      objTable.RegenerateTableSuppressed = False
      ThisDrawing.Regen acActiveViewport
      FormMain.Show
  
End Sub

Private Sub cmbListAlbums_Click()
  'составление списка альбомов
  
  Dim oShifr As ShifrAndAlbums
  Dim oAlbum As Album
  
  'сортировка коллекции альбомов
  Functions.SortyrColShifrs
  
  ListBoxListAlbums.Clear
  For Each oShifr In pcolShifrs
    For Each oAlbum In oShifr.pcolAlbums
      If oAlbum.psShifrAndNum = "" Then
        ListBoxListAlbums.AddItem oShifr.psShifrGBI, 0
      Else
        ListBoxListAlbums.AddItem oShifr.psShifrGBI & ", " & oAlbum.psShifrAndNum, 0
      End If
      ListBoxListAlbums.List(0, 1) = oAlbum.psName
    Next
  Next
  
End Sub

Private Sub cmbScan_Click()
  If psMontagkyFolderPath <> "" Then
    Functions.GetShifrsFromMontagky
  Else
    MsgBox "Папка не найдена", vbCritical, pcsVBProjectName
  End If
End Sub

Private Sub CommandButton3_Click()
  'удаление файла из листбокса
  
  Dim index As Integer
  
  index = ListBoxFilesMS.ListIndex
  If index = -1 Then
    MsgBox "Не выбран файл", vbCritical, pcsVBProjectName
    Exit Sub
  End If
  
  ListBoxFilesMS.RemoveItem index
  
End Sub

Private Sub ListBoxShifrs_Click()
  'вывод списка адьбомов для выбранного шифра
  Dim oShifr As ShifrAndAlbums
  Dim oAlbum As Album
  Dim index As Integer
  Dim i As Integer
  
  index = ListBoxShifrs.ListIndex
  If index = -1 Then
    Exit Sub
  End If
  
  Set oShifr = pcolShifrs(ListBoxShifrs.Text)
  
  ListBoxShifrAlbums.Clear
  If oShifr.pcolAlbums.Count = 0 Then Exit Sub
  For Each oAlbum In oShifr.pcolAlbums
    ListBoxShifrAlbums.AddItem oAlbum.psShifrAndNum, 0
    ListBoxShifrAlbums.List(0, 1) = oAlbum.psName
  Next
End Sub

Private Sub TBMontagkyFolderPath_Exit(ByVal Cancel As MSForms.ReturnBoolean)
  'проверяем папку и выводим список монтажек
  
  'если есть путь к папке с монтажками
  If VBA.Right(TBMontagkyFolderPath, 1) = "\" Then
    psMontagkyFolderPath = VBA.Left(TBMontagkyFolderPath, Len(TBMontagkyFolderPath) - 1)
  Else
    psMontagkyFolderPath = TBMontagkyFolderPath
  End If
  
  If Dir(psMontagkyFolderPath, vbDirectory) <> "" Then
    'вывод списка файлов монтажек
    If MsgBox("Вывести список файлов монтажек", vbInformation + vbYesNo, pcsVBProjectName) = vbYes Then
      Functions.GetListFileMontagek
      'очищаем листбоксы
      FormMain.ListBoxShifrs.Clear
      FormMain.ListBoxListAlbums.Clear
      FormMain.ListBoxShifrAlbums.Clear
    End If
  Else
    psMontagkyFolderPath = ""
    MsgBox "Папка не найдена", vbCritical, pcsVBProjectName
  End If
  
End Sub

Private Sub UserForm_Initialize()
  Functions.LoadFromIni
  GetListFileMontagek
End Sub

Attribute VB_Name = "Functions"
Option Explicit

Public Function GetShifrsFromMontagky()
  'перебор монтажек и составление списка шифров изделий
  'наличие папки уже проверено
  
  'открываем каждый файл монтажек в папке и перебираем блоки
  'и сосмтавляем коллекцию шифров изделий
  
  'Dim oDoc As AxDbDocument
  Dim oDoc As AcadDocument
  Dim oFSO As FileSystemObject
  Dim oMS As AcadModelSpace
  Dim oBlRef As AcadBlockReference
  Dim oEnt As AcadEntity
  Dim oShifr As ShifrAndAlbums
  Dim oAlbum As Album
  Dim vAtr As Variant 'AcadAttributeReference
  Dim sFile As String
  Dim sFolder As String
  Dim sFolderTemp As String
  Dim sLikeName As String
  Dim sString As String
  Dim bolYes As Boolean
  Dim i As Integer
  
  sFolder = psMontagkyFolderPath & "\"
  'sLikeName = FormMain.TBMSFileConsName
  
  For i = 0 To FormMain.ListBoxFilesMS.ListCount - 1
    
    sFile = FormMain.ListBoxFilesMS.List(i)
'        On Error Resume Next
'        oDoc.Open sFolder & sFile
'        If Err Then
'          Err.Clear
'          'файл используется
'          'копируем в temp
'          Set oFSO = New FileSystemObject
'          sFolderTemp = "\\Sgpsrv2\СПД\Конструкторы\Макросы\Temp\"
'          oFSO.CopyFile sFolder & sFile, sFolderTemp & sFile
'          oDoc.Open sFolderTemp & sFile
'        End If
'        On Error GoTo 0

        Set oDoc = Documents.Open(sFolder & sFile)
        Set oMS = oDoc.ModelSpace
        'перебираем все блоки
        For Each oEnt In oMS
          If TypeOf oEnt Is AcadBlockReference Then
            'если есть атрибуты
            If oEnt.HasAttributes = True Then
              'перебираем атрибуты
              Dim bok As Boolean
              bok = False
              For Each vAtr In oEnt.GetAttributes
                If vAtr.Layer = FormMain.TBAtrShifrLayer Then
                    bok = True
                  Exit For
                End If
              Next 'атрибуты
              If bok = True Then
                'добавляем шифр в коллекцию шифров изделий
                Set oShifr = New ShifrAndAlbums
                oShifr.psShifrGBI = vAtr.TextString
                On Error Resume Next
                pcolShifrs.add oShifr, oShifr.psShifrGBI
                On Error GoTo 0
              End If
            End If
          End If
        Next 'объект в ModelSpace
        
        oDoc.Close False
        
  Next 'строка в листбоксе
  
  'выводим список шифров в листбокс
  FormMain.ListBoxShifrs.Clear
  For Each oShifr In pcolShifrs
    FormMain.ListBoxShifrs.AddItem oShifr.psShifrGBI
    'загружаем альбомы из ини
    i = 1
    sString = oIni.GetFile(oShifr.psShifrGBI, CStr(i))
    
'    'проверяем наши альбомы без шифров
'    If InStr(oShifr.psShifrGBI, ".И") > 0 Then
'      If sString = "" Then
'        'подкрашиваем цвет
'        'Как????????
'      End If
'    End If

    While sString <> ""
      Set oAlbum = GetAlbumFromString(sString)
      If Not oAlbum Is Nothing Then
        On Error Resume Next
        oShifr.pcolAlbums.add oAlbum, oAlbum.psName
        On Error GoTo 0
      End If
      i = i + 1
      sString = oIni.GetFile(oShifr.psShifrGBI, CStr(i))
    Wend
  Next
  
End Function

Public Function GetListFileMontagek()
  Dim sFile As String
  Dim sFolder As String
  Dim sLikeName As String
  
  sFolder = psMontagkyFolderPath & "\"
  sLikeName = FormMain.TBMSFileConsName
  
  FormMain.ListBoxFilesMS.Clear
  
  sFile = Dir(sFolder)
  Do While sFile <> ""
    If sFile Like (sLikeName & "*") Then
      If Right(LCase(sFile), 3) = "dwg" Then
        FormMain.ListBoxFilesMS.AddItem sFile
      End If
    End If
    sFile = Dir
  Loop
End Function

Public Function SaveToIni()
  'сохранение параметровы в ини файл
  
  Dim i As Integer
  
  'oIni.CreateIni pcsVBProjectName & ".ini", GetMacroFolder(pcsVBProjectName) & "\Ini"
  
  'папка
  oIni.WriteFile "Настройки", "Папка", psMontagkyFolderPath
  'имя для монтажек
  oIni.WriteFile "Настройки", "МС", FormMain.TBMSFileConsName
  'слой атрибута обозначения
  oIni.WriteFile "Настройки", "СлойОбозначения", FormMain.TBAtrShifrLayer
  'названия альбомов
  For i = 0 To FormAlbum.ComboBox1.ListCount - 1
    oIni.WriteFile "Названия альбомов", CStr(i + 1), FormAlbum.ComboBox1.List(i)
  Next
  oIni.WriteFile "Настройки", "СлойОбозначения", FormMain.TBAtrShifrLayer
  
  'альбомы
  Dim oShifr As ShifrAndAlbums
  Dim oAlbum As Album
  Dim sStringTo As String
  For Each oShifr In pcolShifrs
    i = 0
    For Each oAlbum In oShifr.pcolAlbums
      i = i + 1
      sStringTo = GetStringAlbumToIni(oAlbum)
      oIni.WriteFile oShifr.psShifrGBI, CStr(i), sStringTo
    Next
  Next
  
End Function

Public Function LoadFromIni()
  'загрузка параметров из ини файл
  Dim sValue As String
  Dim i As Integer
  
  oIni.CreateIni pcsVBProjectName & ".ini", GetMacroFolder(pcsVBProjectName) & "\Ini"
  
  'папка
  psMontagkyFolderPath = oIni.GetFile("Настройки", "Папка")
  Functions.RemoveSlashAtEndOfPathFolder psMontagkyFolderPath
  FormMain.TBMontagkyFolderPath = psMontagkyFolderPath
  
  'имя для монтажек
  sValue = oIni.GetFile("Настройки", "МС")
  If sValue <> "" Then
    FormMain.TBMSFileConsName = sValue
  End If
  
  'слой атрибута обозначения
  sValue = oIni.GetFile("Настройки", "СлойОбозначения")
  If sValue <> "" Then
    FormMain.TBAtrShifrLayer = sValue
  End If
  
  'названия альбомов
  i = 1
  sValue = oIni.GetFile("Названия альбомов", CStr(i))
  Do While sValue <> ""
    If sValue <> "" Then
      FormAlbum.ComboBox1.AddItem sValue
    End If
    i = i + 1
    sValue = oIni.GetFile("Названия альбомов", CStr(i))
  Loop
  
End Function

Public Function GetMacroFolder(strVBProjectName) As String
   'получение пути к корню макроса
   'без \
   
   Dim strMacroFolder As String
   Dim intValue As Integer
   
   On Error GoTo HasError
   
   strMacroFolder = Application.VBE.vbprojects.Item(strVBProjectName).FileName
   intValue = InStrRev(strMacroFolder, "\")
   strMacroFolder = Left(strMacroFolder, intValue - 1) 'корень с макросом, без \ на конце
   
   GetMacroFolder = strMacroFolder
   
Exit Function

HasError:
   Select Case Err.Number
      Case Else
         MsgBox "Functions, GetMacroFolder" & vbCrLf & _
               Err.Description
   End Select
   
End Function

Public Function GetStringAlbumToIni(oAlbum As Album) As String
  'строка номера альбома и названия: "Альбом 1;Наружные стеновые панели"
  GetStringAlbumToIni = oAlbum.psShifrAndNum & ";" & oAlbum.psName
End Function

Public Function GetAlbumFromString(sString) As Album
  Dim iValue As Integer
  
  iValue = InStr(sString, ";")
  If iValue <> 0 Then
    Set GetAlbumFromString = New Album
    GetAlbumFromString.psShifrAndNum = Left(sString, iValue - 1)
    GetAlbumFromString.psName = Right(sString, Len(sString) - iValue)
  End If
End Function

Public Function SortyrColShifrs()
  
  Dim i As Integer
  Dim j As Integer
  Dim oShifr As ShifrAndAlbums
  Dim oAlbum As Album
  
  For i = 1 To pcolShifrs.Count - 1
    For j = 1 To pcolShifrs.Count - i
      If StrComp(pcolShifrs.Item(j).psShifrGBI, pcolShifrs.Item(j + 1).psShifrGBI) = -1 Then
        Set oShifr = pcolShifrs.Item(j)
        pcolShifrs.Remove j
        pcolShifrs.add oShifr, oShifr.psShifrGBI, , j
      End If
    Next
  Next
  For Each oShifr In pcolShifrs
    For i = 1 To oShifr.pcolAlbums.Count - 1
      For j = 1 To oShifr.pcolAlbums.Count - i
        If StrComp(oShifr.pcolAlbums.Item(j).psShifrAndNum, oShifr.pcolAlbums.Item(j + 1).psShifrAndNum) = -1 Then
          Set oAlbum = oShifr.pcolAlbums.Item(j)
          oShifr.pcolAlbums.Remove j
          oShifr.pcolAlbums.add oAlbum, oAlbum.psName, , j
        End If
      Next
    Next
  Next
  
End Function

Public Function MakeTableStyleForSpec(strTableStyleName As String) As String
   'создание табличного стиля для спецификаций
   'для масштаба 1:1, в конкретных условиях нужно отмасштабировать после заполнения
   
   Dim strTextStyleName As String
   strTextStyleName = strTableStyleName
   Dim objTableStyle As AcadTableStyle
   Dim objTextStyle As AcadTextStyle
   Dim objDictTableStyle As AcadDictionary
   Dim bolYes As Boolean
   
   'создаем табличный стиль в словаре чертежа
   Set objDictTableStyle = ThisDrawing.Dictionaries.Item("ACAD_TABLESTYLE")
   
   'проверяем есть ли уже такой табл стиль
   For Each objTableStyle In objDictTableStyle
      If objTableStyle.Name = strTableStyleName Then
         'переделывать не буду ????????????
         Exit Function
      End If
   Next
'   On Error Resume Next 'не хорошо конечно, надо сделать проверки
   Set objTableStyle = objDictTableStyle.AddObject(strTableStyleName, "AcDbTableStyle")
   
   'создаем текстовый стиль для таблиц
   For Each objTextStyle In ThisDrawing.TextStyles
      If objTextStyle.Name = strTextStyleName Then
         bolYes = True
      End If
   Next
   If bolYes = False Then
      Set objTextStyle = ThisDrawing.TextStyles.add(strTextStyleName)
      'задаем шрифт, у нас принят ариал
      objTextStyle.SetFont "Arial", False, False, 0, 34 'значения получил по GetFont для нужного стиля
   End If
'   On Error GoTo 0

   'настраиваем таблицу
   'задаем текстовый стиль всем типам ячеек
   objTableStyle.SetTextStyle AcRowType.acDataRow + AcRowType.acHeaderRow _
                           + AcRowType.acTitleRow + AcRowType.acUnknownRow, strTextStyleName
   'задаем высоту текста
   objTableStyle.SetTextHeight AcRowType.acDataRow + AcRowType.acUnknownRow, 2.5
   objTableStyle.SetTextHeight AcRowType.acHeaderRow + AcRowType.acTitleRow, 3
   'задаем выравниваниев ячейках
   objTableStyle.SetAlignment AcRowType.acHeaderRow + AcRowType.acTitleRow, acMiddleCenter
   objTableStyle.SetAlignment AcRowType.acDataRow + AcRowType.acUnknownRow, acMiddleLeft
   'задаем отступы в ячейках
   objTableStyle.HorzCellMargin = 1.5
   objTableStyle.VertCellMargin = 1
   'задаем толщины границ
   objTableStyle.SetGridLineWeight AcGridLineType.acHorzBottom + AcGridLineType.acHorzInside + AcGridLineType.acHorzTop _
                + AcGridLineType.acVertInside + AcGridLineType.acVertLeft + AcGridLineType.acVertRight, _
                AcRowType.acTitleRow + AcRowType.acHeaderRow, AcLineWeight.acLnWt050
   objTableStyle.SetGridLineWeight AcGridLineType.acHorzBottom + AcGridLineType.acHorzTop + _
               AcGridLineType.acVertInside + AcGridLineType.acVertLeft + AcGridLineType.acVertRight, _
               AcRowType.acDataRow + AcRowType.acUnknownRow, AcLineWeight.acLnWt050
   objTableStyle.SetGridLineWeight AcGridLineType.acHorzInside, _
               AcRowType.acDataRow + AcRowType.acUnknownRow, AcLineWeight.acLnWt025
   'задаем цвет тексту
   Dim color As New AcadAcCmColor
   'color.Red
   'color.SetRGB 255, 0, 0
   objTableStyle.SetColor AcRowType.acDataRow + AcRowType.acHeaderRow _
                        + AcRowType.acTitleRow + AcRowType.acUnknownRow, color
   
   'вроде все, посмотрим
   
   'возвращаем имя созданного стиля
   MakeTableStyleForSpec = strTableStyleName
   
End Function

Public Function RemoveSlashAtEndOfPathFolder(ByRef sPath As String)
  If Right(sPath, 1) = "\" Then 'убираем его
      sPath = Mid(sPath, 1, Len(sPath) - 1)
   End If
End Function

Attribute VB_Name = "Main"
Option Explicit

  Public Const pcsVBProjectName As String = "MSListAlbums"
  Public psMontagkyFolderPath As String
  Public pcolShifrs As New Collection
  Public oIni As New ClassINI

Public Sub Main()
  'вывод списка использующихся альбомов в монтажных схемах
  
  FormMain.Show
  
End Sub

Attribute VB_Name = "ShifrAndAlbums"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'шифр жб изделий и список альбомов в него входящих

Public psShifrGBI As String
Public pcolAlbums As New Collection
