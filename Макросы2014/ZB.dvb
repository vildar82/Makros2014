Attribute VB_Name = "Browse2"
'Option Explicit
'
'Private Type BrowseInfo
'  hWndOwner As Long
'  pIDLRoot As Long
'  pszDisplayName As Long
'  lpszTitle As Long
'  ulFlags As Long
'  lpfnCallback As Long
'  lParam As Long
'  iImage As Long
'End Type
''
'' просмотр каталогов
''
'' для выбора каталога,
'' чтобы начать поиск документа
'Private Const BIF_RETURNONLYFSDIRS = &H1
'' для запуска команды Find
'Private Const BIF_DONTGOBELOWDOMAIN = &H2
'Private Const BIF_STATUSTEXT = &H4
'Private Const BIF_RETURNFSANCESTORS = &H8
'' просмотр компьютеров
'Private Const BIF_BROWSEFORCOMPUTER = &H1000
'' просмотр принтеров
'Private Const BIF_BROWSEFORPRINTER = &H2000
'' просмотр всего
'Private Const BIF_BROWSEINCLUDEFILES = &H4000
''
'Private Const MAX_PATH = 260
'Private Declare PtrSafe Sub CoTaskMemFree Lib "ole32.dll" _
'  (ByVal hMem As Long)
'Private Declare PtrSafe Function lstrcat Lib "kernel32" Alias "lstrcatA" _
'  (ByVal lpString1 As String, ByVal lpString2 As String) As Long
'Private Declare PtrSafe Function SHBrowseForFolder Lib "shell32" _
'  (lpbi As BrowseInfo) As Long
'Private Declare PtrSafe Function SHGetPathFromIDList Lib "shell32" _
'  (ByVal pidList As Long, ByVal lpBuffer As String) As Long
'
'Public Function BrowseForFolder(hWndOwner As Long, _
'  sPrompt As String) As String
'  '==================================================
'  ' Открывает системное диалоговое окно для просмотра каталогов
'  '==================================================
'  Dim iNull As Integer
'  Dim lpIDList As Long
'  Dim lResult As Long
'  Dim sPath As String
'  Dim udtBI As BrowseInfo
'  '
'  With udtBI
'    .hWndOwner = hWndOwner
'    .lpszTitle = lstrcat(sPrompt, "")
'    .ulFlags = BIF_RETURNONLYFSDIRS
'  End With
'  lpIDList = SHBrowseForFolder(udtBI)
'  If lpIDList Then
'    sPath = String$(MAX_PATH, 0)
'    lResult = SHGetPathFromIDList(lpIDList, sPath)
'    Call CoTaskMemFree(lpIDList)
'    iNull = InStr(sPath, vbNullChar)
'    If iNull Then sPath = Left$(sPath, iNull - 1)
'    'End If
'  End If
'  BrowseForFolder = sPath
'End Function
'
'Public Sub Туст_папки()
'   Dim MyStr As String
'  MyStr = BrowseForFolder(hwnd, "Привет всем!")
'  MsgBox MyStr
'End Sub

Attribute VB_Name = "BrowseDialog"
Option Explicit
'----------------------------------------------------------------------
' 64 bit VBA 7 version of File and Folder Browswers
' FileBrowseOpen()
' FileBrowseSave()
' FolderBrowse()
' Much of the original 32 bit module was donated by the good people of XtremeVbTalk.com
' I massaged it to be 64 bit with VBA 7 code lifted from numerous sites on the web
'----------------------------------------------------------------------

Private Declare PtrSafe Function GetOpenFileName Lib "comdlg32.dll" Alias _
"GetOpenFileNameA" (pOpenfilename As OPENFILENAME) As Long

Private Declare PtrSafe Function GetSaveFileName Lib "comdlg32.dll" Alias _
"GetSaveFileNameA" (pOpenfilename As OPENFILENAME) As Long

Private Declare PtrSafe Function SHBrowseForFolder Lib "shell32.dll" _
Alias "SHBrowseForFolderA" (lpBrowseInfo As BrowseInfo) As Long

Private Declare PtrSafe Function SHGetPathFromIDList Lib "shell32.dll" _
(ByVal pidList As LongPtr, ByVal lpBuffer As String) As Long


Public Declare PtrSafe Function SendMessageA Lib "user32" _
(ByVal Hwnd As LongPtr, ByVal wMsg As Long, _
ByVal wParam As LongPtr, lParam As Any) As LongPtr

Private Declare PtrSafe Sub CoTaskMemFree Lib "ole32.dll" (ByVal hMem As LongPtr)

Private Const BIF_RETURNONLYFSDIRS As Long = 1
Private Const CSIDL_DRIVES As Long = &H11
Private Const WM_USER As Long = &H400
Private Const MAX_PATH As Long = 260
'// message from browser
Private Const BFFM_INITIALIZED As Long = 1
Private Const BFFM_SELCHANGED As Long = 2
Private Const BFFM_VALIDATEFAILEDA As Long = 3 '// lParam:szPath ret:1(cont),0(EndDialog)
Private Const BFFM_VALIDATEFAILEDW As Long = 4 '// lParam:wzPath ret:1(cont),0(EndDialog)
Private Const BFFM_IUNKNOWN As Long = 5 '// provides IUnknown to client. lParam: IUnknown*
'// messages to browser
Private Const BFFM_SETSTATUSTEXTA As Long = WM_USER + 100
Private Const BFFM_ENABLEOK As Long = WM_USER + 101
Private Const BFFM_SETSELECTIONA As Long = WM_USER + 102
Private Const BFFM_SETSELECTIONW As Long = WM_USER + 103
Private Const BFFM_SETSTATUSTEXTW As Long = WM_USER + 104
Private Const BFFM_SETOKTEXT As Long = WM_USER + 105 '// Unicode only
Private Const BFFM_SETEXPANDED As Long = WM_USER + 106 '// Unicode only


Private Type OPENFILENAME
lStructSize As Long
hWndOwner As LongPtr
hInstance As LongPtr
lpstrFilter As String
lpstrCustomFilter As String
nMaxCustFilter As Long
nFilterIndex As Long
lpstrFile As String
nMaxFile As Long
lpstrFileTitle As String
nMaxFileTitle As Long
lpstrInitialDir As String
lpstrTitle As String
flags As Long
nFileOffset As Integer
nFileExtension As Integer
lpstrDefExt As String
lCustData As Long
lpfnHook As LongPtr
lpTemplateName As String
End Type
Public Type BrowseInfo
hWndOwner As LongPtr
pIDLRoot As LongPtr
pszDisplayName As String
lpszTitle As String
ulFlags As Long
lpfnCallback As LongPtr
lParam As LongPtr
iImage As Long
End Type
 
'====== File Browsers for 64 bit VBA 7 ========
Public Function FileBrowseOpen(ByVal sInitFolder As String, _
ByVal sTitle As String, _
ByVal sFilter As String, _
ByVal nFilterIndex As Integer) As String


Dim OpenFile As OPENFILENAME
Dim lReturn As Long

sInitFolder = CorrectPath(sInitFolder)


OpenFile.lpstrInitialDir = sInitFolder

' Swap filter separator for api separator
sFilter = Replace(sFilter, "|", Chr(0))



OpenFile.lpstrFilter = sFilter
OpenFile.nFilterIndex = nFilterIndex
OpenFile.lpstrTitle = sTitle


OpenFile.hWndOwner = 0
OpenFile.lpstrFile = String(257, 0)
OpenFile.nMaxFile = LenB(OpenFile.lpstrFile) - 1
OpenFile.lStructSize = LenB(OpenFile)

OpenFile.lpstrFileTitle = OpenFile.lpstrFile
OpenFile.nMaxFileTitle = OpenFile.nMaxFile

OpenFile.flags = 0

lReturn = GetOpenFileName(OpenFile)

If lReturn = 0 Then
FileBrowseOpen = ""
Else
FileBrowseOpen = Trim(Left(OpenFile.lpstrFile, InStr(1, OpenFile.lpstrFile, vbNullChar) - 1))
End If
End Function
Public Function FileBrowseSave(ByVal sDefaultFilename As String, _
ByVal sInitFolder As String, _
ByVal sTitle As String, _
ByVal sFilter As String, _
ByVal nFilterIndex As Integer) As String
Dim PadCount As Integer
Dim OpenFile As OPENFILENAME
Dim lReturn As Long

sInitFolder = CorrectPath(sInitFolder)

' Swap filter separator for api separator
sFilter = Replace(sFilter, "|", Chr(0))

OpenFile.lpstrFilter = sFilter
OpenFile.nFilterIndex = 1
OpenFile.hWndOwner = 0

PadCount = 260 - Len(sDefaultFilename)
OpenFile.lpstrFile = sDefaultFilename & String(PadCount, Chr(0))
'OpenFile.lpstrFile = String(257, 0)
OpenFile.nMaxFile = LenB(OpenFile.lpstrFile) - 1
OpenFile.lStructSize = LenB(OpenFile)

OpenFile.lpstrFileTitle = OpenFile.lpstrFile
OpenFile.nMaxFileTitle = OpenFile.nMaxFile
OpenFile.lpstrInitialDir = sInitFolder
OpenFile.lpstrTitle = sTitle
OpenFile.flags = 0
lReturn = GetSaveFileName(OpenFile)

If lReturn = 0 Then
FileBrowseSave = ""
Else
FileBrowseSave = Trim(Left(OpenFile.lpstrFile, InStr(1, OpenFile.lpstrFile, vbNullChar) - 1))
End If
End Function
 

'====== Folder Browser for 64 bit VBA 7 ========
Public Function FolderBrowse(ByVal sDialogTitle As String, ByVal sInitFolder As String) As String
Dim ReturnPath As String

Dim b(MAX_PATH) As Byte
Dim pItem As Long
Dim sFullPath As String
Dim bi As BrowseInfo
Dim ppidl As Long

sInitFolder = CorrectPath(sInitFolder)

' Note VBA windows and dialogs do not have an hWnd property.
bi.hWndOwner = 0 'Windows Main Screen handle.

' SHGetSpecialFolderLocation bi.hWndOwner, CSIDL_DRIVES, ppidl

bi.pIDLRoot = 0 'ppidl


bi.pszDisplayName = VarPtr(b(0))
bi.lpszTitle = sDialogTitle
bi.ulFlags = BIF_RETURNONLYFSDIRS
If FolderExists(sInitFolder) Then bi.lpfnCallback = PtrToFunction(AddressOf BFFCallback)
bi.lParam = StrPtr(sInitFolder)
pItem = SHBrowseForFolder(bi)

If pItem Then ' Succeeded
sFullPath = Space$(MAX_PATH)
If SHGetPathFromIDList(pItem, sFullPath) Then
ReturnPath = Left$(sFullPath, InStr(sFullPath, vbNullChar) - 1) ' Strip nulls
CoTaskMemFree pItem
End If
End If

If ReturnPath <> "" Then
If Right$(ReturnPath, 1) <> "\" Then
ReturnPath = ReturnPath & "\"
End If
End If

FolderBrowse = ReturnPath

End Function
' typedef int (CALLBACK* BFFCALLBACK)(HWND hwnd, UINT uMsg, LPARAM lParam, LPARAM lpData);
Private Function BFFCallback(ByVal Hwnd As LongPtr, ByVal uMsg As LongPtr, ByVal lParam As LongPtr, ByVal sData As String) As LongPtr
If uMsg = BFFM_INITIALIZED Then
SendMessageA Hwnd, BFFM_SETSELECTIONA, True, ByVal sData
End If
End Function
Private Function PtrToFunction(ByVal lFcnPtr As LongPtr) As LongPtr
PtrToFunction = lFcnPtr
End Function
Private Function CorrectPath(ByVal sPath As String) As String
If Right$(sPath, 1) = "\" Then
If Len(sPath) > 3 Then sPath = Left$(sPath, Len(sPath) - 1) ' Strip backslash from non-root
Else
If Len(sPath) = 2 Then sPath = sPath & "\" ' Append backslash to root
End If
CorrectPath = sPath
End Function

Public Function FolderExists(ByVal sFolderName As String) As Boolean
Dim att As Long
On Error Resume Next
att = GetAttr(sFolderName)
If Err.Number = 0 Then
FolderExists = True
Else
Err.Clear
FolderExists = False
End If
On Error GoTo 0
End Function

Attribute VB_Name = "BrowseFolder"
'Option Explicit
'
'Declare PtrSafe Function GetDC Lib "user32" (ByVal hwnd As Long) As Long
'Declare PtrSafe Function ReleaseDC Lib "user32" (ByVal hwnd As Long, _
'  ByVal hDC As Long) As Long
'Declare PtrSafe Function GetDeviceCaps Lib "gdi32" (ByVal hDC As Long, _
'  ByVal nIndex As Long) As Long
'
'Const HWND_DESKTOP As Long = 0
'Const LOGPIXELSX As Long = 88
'Const LOGPIXELSY As Long = 90
'Const HORZRES As Long = 8
'Const VERTRES As Long = 10
'
'
'Public Type RECT
'    Left As Long
'    Top As Long
'    Right As Long
'    Bottom As Long
'End Type
'
'Public Declare PtrSafe Function MoveWindow Lib "user32.dll" ( _
'     ByVal hwnd As Long, _
'     ByVal X As Long, _
'     ByVal y As Long, _
'     ByVal nWidth As Long, _
'     ByVal nHeight As Long, _
'     ByVal bRepaint As Long) As Long
'
'Public Declare PtrSafe Function GetWindowRect Lib "user32.dll" ( _
'     ByVal hwnd As Long, _
'     lpRect As RECT) As Long
'
'Public Declare PtrSafe Function WaitForInputIdle Lib "user32" ( _
'    ByVal hProcess As Long, _
'    ByVal dwMilliseconds As Long) As Long
'
'Public Declare PtrSafe Function FindWindowEx Lib "user32.dll" Alias "FindWindowExA" ( _
'     ByVal hWnd1 As Long, _
'     ByVal hWnd2 As Long, _
'     ByVal lpsz1 As String, _
'     ByVal lpsz2 As String) As Long
'
'Public Declare PtrSafe Function EnumThreadWindows Lib "user32" _
'    (ByVal dwThreadId As Long, _
'    ByVal lpfn As Long, _
'    ByVal lParam As Long) As Long
'
'Public Declare PtrSafe Function GetWindowThreadProcessId Lib "user32.dll" ( _
'     ByVal hwnd As Long, _
'     lpdwProcessId As Long) As Long
'
'Public Declare PtrSafe Function SetWindowPos Lib "user32.dll" ( _
'     ByVal hwnd As Long, _
'     ByVal hWndInsertAfter As Long, _
'     ByVal X As Long, _
'     ByVal y As Long, _
'     ByVal cx As Long, _
'     ByVal cy As Long, _
'     ByVal wFlags As Long) As Long
'
'Public Declare PtrSafe Function SetWindowText Lib "user32.dll" Alias "SetWindowTextA" ( _
'     ByVal hwnd As Long, _
'     ByVal lpString As String) As Long
'
'Public Const SWP_SHOWWINDOW = &H40
'Public Const HWND_TOPMOST = -1
'
'Public g_CurrentDirectory As String
'Public g_FileMasks() As String
'Public g_ChangeSize As Boolean
'Public g_DialogTitle As String
'Public g_RatioX As Double, g_RatioY As Double
'Public g_CenterOnScreen As Boolean
'Public g_TopMost As Boolean
'
'Public g_newLeft As Long, g_newTop As Long
'Public g_deltaH As Long, g_deltaW As Long
'
'Public Const WM_USER As Long = &H400
'Public Const BFFM_INITIALIZED = 1
'Public Const BFFM_SELCHANGED = 2
'Public Const BFFM_SETSTATUSTEXT = (WM_USER + 100)
'Public Const BFFM_ENABLEOK = (WM_USER + 101)
'Public Const BFFM_SETSELECTION = (WM_USER + 102)
'
'Public Type BrowseInfo
'    hWndOwner As Long
'    pIDLRoot As Long
'    pszDisplayName As Long
'    lpszTitle As Long
'    ulFlags As Long
'    lpfnCallback As Long
'    lParam As Long
'    iImage As Long
'End Type
'
'Public Enum WhatBrowse
'    BIF_RETURNONLYFSDIRS = &H1
'    BIF_BROWSEINCLUDEFILES = &H1 Or &H4000
'    BIF_BROWSEFORCOMPUTER = &H1000
'    BIF_BROWSEFORPRINTER = &H2000
'    BIF_DONTGOBELOWDOMAIN = &H2
'    BIF_STATUSTEXT = &H4
'    BIF_NEWDIALOGSTYLE = &H40
'    BIF_EDITBOX = &H10
'    BIF_USENEWUI = (BIF_NEWDIALOGSTYLE Or BIF_EDITBOX)
'    BIF_RETURNFSANCESTORS = &H8
'End Enum
'
'Public Const MAX_PATH = 260&
'Public Declare PtrSafe Function SendMessage Lib "user32" Alias "SendMessageA" _
'  (ByVal hwnd As Long, _
'   ByVal wMsg As Long, _
'   ByVal wParam As Long, _
'   lParam As Any) As Long
'Public Declare PtrSafe Sub CoTaskMemFree Lib "ole32.dll" (ByVal hMem As Long)
'Public Declare PtrSafe Function lstrcat Lib "kernel32" Alias "lstrcatA" _
'    (ByVal lpString1 As String, _
'    ByVal lpString2 As String) As Long
'Public Declare PtrSafe Function SHBrowseForFolder Lib "shell32" (lpbi As BrowseInfo) As Long
'Public Declare PtrSafe Function SHGetPathFromIDList Lib "shell32" _
'    (ByVal pidList As Long, _
'    ByVal lpBuffer As String) As Long
'
'Public Function fBrowseForFolder(ByVal hWnd_Owner As Long, _
'                                 ByVal sPrompt As String, _
'                                 ByVal WhatBr As Long, _
'                                 ByVal DialogTitle As String, _
'                                 Optional ByVal initDir As String = "", _
'                                 Optional ByRef fileMasks As String = "", _
'                                 Optional ByVal ChangeSize As Boolean = False, _
'                                 Optional ByVal RatioX As Double = 1, _
'                                 Optional ByVal RatioY As Double = 1, _
'                                 Optional ByVal CenterOnScreen As Boolean = False, _
'                                 Optional ByVal PromptColor As Long = 0&, _
'                                 Optional ByVal PathColor As Long = 0&, _
'                                 Optional ByVal TopMost As Boolean) As String
'
'    Dim iNull As Integer
'    Dim lpIDList As Long
'    Dim lResult As Long
'    Dim sPath As String
'    Dim udtBI As BrowseInfo
'
'    g_DialogTitle = DialogTitle
'    g_ChangeSize = ChangeSize
'    g_RatioX = RatioX
'    g_RatioY = RatioY
'    g_CenterOnScreen = CenterOnScreen
'    g_TopMost = TopMost
'
'    If initDir = "" Then
'        g_CurrentDirectory = ""
'    Else
'        g_CurrentDirectory = initDir & vbNullChar
'    End If
'
'    If fileMasks = "" Then
'        ReDim g_FileMasks(0 To 0)
'        g_FileMasks(0) = ""
'    Else
'        g_FileMasks = Split(fileMasks, "|")
'    End If
'
'    With udtBI
'        .hWndOwner = hWnd_Owner
'        .lpszTitle = lstrcat(sPrompt, "")
'        .ulFlags = WhatBr
'        .lpfnCallback = GetAddressofFunction(AddressOf BrowseCallbackProc)  'get address of function.
'    End With
'    lpIDList = SHBrowseForFolder(udtBI)
'
'    If lpIDList Then
'        sPath = String$(MAX_PATH, 0)
'        lResult = SHGetPathFromIDList(lpIDList, sPath)
'        Call CoTaskMemFree(lpIDList)
'        iNull = InStr(sPath, vbNullChar)
'        If iNull Then sPath = Left$(sPath, iNull - 1)
'    End If
'    fBrowseForFolder = sPath
'
'End Function
'
'Public Function BrowseCallbackProc(ByVal hwnd As Long, ByVal uMsg As Long, ByVal lp As Long, ByVal pData As Long) As Long
'
'    Dim lpIDList As Long
'    Dim ret As Long
'    Dim sBuffer As String
'    Dim i As Integer, flag As Boolean, sPath As String
'
'    On Error Resume Next
'
'    Select Case uMsg
'
'        Case BFFM_INITIALIZED
'            If g_CurrentDirectory <> "" Then
'                Call SendMessage(hwnd, BFFM_SETSELECTION, 1, ByVal g_CurrentDirectory)
'            End If
'
'            SetWindowText hwnd, g_DialogTitle
'            If g_ChangeSize Then
'                Call ResizeDialog(hwnd)
'
'            Else
'                If g_CenterOnScreen Then Call CenterDialog(hwnd)
'            End If
'
'        Case BFFM_SELCHANGED
'            sBuffer = Space$(MAX_PATH)
'
'            ret = SHGetPathFromIDList(lp, sBuffer)
'            If ret = 1 Then
'                Call SendMessage(hwnd, BFFM_SETSTATUSTEXT, 0, ByVal sBuffer)
'                If g_FileMasks(0) <> "" Then
'                    sPath = Left$(sBuffer, InStr(1, sBuffer, vbNullChar) - 1)
'                    If Right$(sPath, 1) <> "\" Then sPath = sPath + "\"
'                    flag = False
'                    For i = 0 To UBound(g_FileMasks)
'                        If Dir(sPath + g_FileMasks(i)) <> "" Then flag = True
'                    Next i
'                    If flag Then
'                        Call SendMessage(hwnd, BFFM_ENABLEOK, 0, ByVal 1&)
'                    Else
'                        Call SendMessage(hwnd, BFFM_ENABLEOK, 0, ByVal 0&)
'                    End If
'                End If
'            End If
'
'        Case Else
'    End Select
'
'    BrowseCallbackProc = 0
'
'End Function
'
'Public Function GetAddressofFunction(add As Long) As Long
'    GetAddressofFunction = add
'End Function
'
'Private Sub ResizeDialog(ByVal hwnd As Long)
'    Dim pid As Long, thread_id As Long
'    Dim screenWidth As Long, screenHeight As Long
'    Dim winWidth As Long, winHeight As Long
'    Dim R As RECT
'    Dim lngDC As Long
'    Dim lWidth As Long
'    Dim lHeight As Long
'
'    lngDC = GetDC(HWND_DESKTOP)
'    screenWidth = GetDeviceCaps(lngDC, HORZRES)
'    screenHeight = GetDeviceCaps(lngDC, VERTRES)
'
'    GetWindowRect hwnd, R
'
'    winWidth = (R.Right - R.Left) * g_RatioX
'    winHeight = (R.Bottom - R.Top) * g_RatioY
'    g_deltaH = winHeight - (R.Bottom - R.Top)
'    g_deltaW = winWidth - (R.Right - R.Left)
'
'    If g_CenterOnScreen Then
'        g_newLeft = (screenWidth - winWidth) / 2
'        g_newTop = (screenHeight - winHeight) / 2
'    Else
'        g_newLeft = R.Left
'        g_newTop = R.Top
'    End If
'
'    If g_TopMost Then
'        SetWindowPos hwnd, HWND_TOPMOST, g_newLeft, g_newTop, winWidth, winHeight, SWP_SHOWWINDOW
'    Else
'        SetWindowPos hwnd, 0, g_newLeft, g_newTop, winWidth, winHeight, SWP_SHOWWINDOW
'    End If
'
'    thread_id = GetWindowThreadProcessId(hwnd, pid)
'    Call WaitForInputIdle(pid, 1000&)
'    EnumThreadWindows thread_id, AddressOf EnumThreadWndProc, 0&
'
'End Sub
'
''--------------------------------------------------
'Function TwipsPerPixelX() As Single
''--------------------------------------------------
''Returns the width of a pixel, in twips.
''--------------------------------------------------
'  Dim lngDC As Long
'  lngDC = GetDC(HWND_DESKTOP)
'  TwipsPerPixelX = 1440& / GetDeviceCaps(lngDC, LOGPIXELSX)
'  ReleaseDC HWND_DESKTOP, lngDC
'End Function
'
''--------------------------------------------------
'Function TwipsPerPixelY() As Single
''--------------------------------------------------
''Returns the height of a pixel, in twips.
''--------------------------------------------------
'  Dim lngDC As Long
'  lngDC = GetDC(HWND_DESKTOP)
'  TwipsPerPixelY = 1440& / GetDeviceCaps(lngDC, LOGPIXELSY)
'  ReleaseDC HWND_DESKTOP, lngDC
'End Function
'
'Public Function EnumThreadWndProc(ByVal hwnd As Long, ByVal lParam As Long) As Long
'    Dim treeHwnd As Long, okButtonHwnd As Long, cancelButtonHwnd As Long, promptHwnd As Long, folderHwnd As Long
'    Dim R As RECT
'    Static allControlsAdjusted As Integer
'
'    okButtonHwnd = FindWindowEx(hwnd, ByVal 0&, "Button", vbNullString)
'    If okButtonHwnd <> 0 Then
'        GetWindowRect okButtonHwnd, R
'        MoveWindow okButtonHwnd, (R.Left - g_newLeft - 3) + g_deltaW, (R.Top - g_newTop - 22) + g_deltaH, R.Right - R.Left, R.Bottom - R.Top, 1
'        allControlsAdjusted = allControlsAdjusted + 10000
'        cancelButtonHwnd = FindWindowEx(hwnd, okButtonHwnd, "Button", vbNullString)
'        If cancelButtonHwnd <> 0 Then
'            GetWindowRect cancelButtonHwnd, R
'            MoveWindow cancelButtonHwnd, (R.Left - g_newLeft - 3) + g_deltaW, (R.Top - g_newTop - 22) + g_deltaH, R.Right - R.Left, R.Bottom - R.Top, 1
'            allControlsAdjusted = allControlsAdjusted + 1000
'        End If
'    End If
'
'    treeHwnd = FindWindowEx(hwnd, ByVal 0&, "SysTreeView32", vbNullString)
'    If treeHwnd <> 0 Then
'        GetWindowRect treeHwnd, R
'        MoveWindow treeHwnd, R.Left - g_newLeft - 3, R.Top - g_newTop - 22, (R.Right - R.Left) + g_deltaW, (R.Bottom - R.Top) + g_deltaH, 1
'        allControlsAdjusted = allControlsAdjusted + 100
'    End If
'
'    promptHwnd = FindWindowEx(hwnd, ByVal 0&, "Static", vbNullString)
'    If promptHwnd <> 0 Then
'        GetWindowRect promptHwnd, R
'        MoveWindow promptHwnd, R.Left - g_newLeft - 3, R.Top - g_newTop - 22, (R.Right - R.Left) + g_deltaW, R.Bottom - R.Top, 1
'        allControlsAdjusted = allControlsAdjusted + 10
'        folderHwnd = FindWindowEx(hwnd, promptHwnd, "Static", vbNullString)
'        If folderHwnd <> 0 Then
'            GetWindowRect folderHwnd, R
'            MoveWindow folderHwnd, R.Left - g_newLeft - 3, R.Top - g_newTop - 22, (R.Right - R.Left) + g_deltaW, R.Bottom - R.Top, 1
'            allControlsAdjusted = allControlsAdjusted + 1
'        End If
'    End If
'
'    EnumThreadWndProc = Not (allControlsAdjusted = 11111)
'End Function
'
'Private Sub CenterDialog(ByVal hwnd As Long)
'    Dim screenWidth As Long, screenHeight As Long
'    Dim winWidth As Long, winHeight As Long
'    Dim R As RECT
'    Dim lngDC As Long
'    Dim lWidth As Long
'    Dim lHeight As Long
'
'    lngDC = GetDC(HWND_DESKTOP)
'    screenWidth = GetDeviceCaps(lngDC, HORZRES)
'    screenHeight = GetDeviceCaps(lngDC, VERTRES)
'
'    GetWindowRect hwnd, R
'
'    winWidth = (R.Right - R.Left)
'    winHeight = (R.Bottom - R.Top)
'
'    g_newLeft = (screenWidth - winWidth) / 2
'    g_newTop = (screenHeight - winHeight) / 2
'
'    SetWindowPos hwnd, 0, g_newLeft, g_newTop, winWidth, winHeight, SWP_SHOWWINDOW
'End Sub
'
'
'Public Sub Тест_выбор_папки()
'
'   Dim st As String
'   Dim lngDC As Long
'
'   lngDC = GetDC(HWND_DESKTOP)
'
'    st = fBrowseForFolder(0&, _
'                          "Внимание: вложенные папки не учиываются." & vbCrLf & _
'                                    "Поэтому выбирайте каждый каталог по отдельности." & vbCrLf & _
'                                    "Можно выбрать только папку содержащую файлы dwg!", _
'                          BIF_RETURNONLYFSDIRS, _
'                          "Выберите папку c блоками", _
'                          "\\Sgpsrv2\спд\Конструкторы\Пан. Кронверк( 17 эт.)\От архитекторов 2.10.08", _
'                          "*.DWG*", _
'                          True, _
'                          1, _
'                          1, _
'                          True, _
'                          0, _
'                          0, _
'                          True)
'    If Len(st) > 0 Then MsgBox "Вы выбрали папку:" + vbCr + st, vbInformation, "Информация"
'
'End Sub

Attribute VB_Name = "ClassINI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
 
Private strInI As String
 
'// Win API Declares
Private Declare PtrSafe Function WritePrivateProfileString _
  Lib "kernel32" Alias "WritePrivateProfileStringA" _
 (ByVal lpApplicationName As String, _
  ByVal lpKeyName As Any, _
  ByVal lpString As Any, _
  ByVal lpFileName As String) As Long
 
Private Declare PtrSafe Function GetPrivateProfileString _
  Lib "kernel32" Alias "GetPrivateProfileStringA" _
 (ByVal lpApplicationName As String, _
  ByVal lpKeyName As Any, _
  ByVal lpDefault As String, _
  ByVal lpReturnedString As String, _
  ByVal nSize As Long, _
  ByVal lpFileName As String) As Long
 
Private Function MakePath(ByVal strFileName As String, _
  ByVal strPath As String) As String
 
 '// Makes an INI file: Guarantees a sub dir
 Do While Right$(strPath, 1) = "\"
   strPath = Left$(strPath, Len(strPath) - 1)
 Loop
 
 Do While Left$(strFileName, 1) = "\"
   strFileName = Mid$(strFileName, 2)
 Loop
 
 '// Return the path
 MakePath = strPath & "\" & strFileName
End Function
 
Public Sub CreateIni(strFileName As String, strPath As String)
 '// Make a new ini file
 strInI = MakePath(strFileName, strPath)
End Sub
 
Public Sub WriteFile(strSection As String, _
 strKey As String, _
 strValue As String)
 
 '// Write to strINI
 WritePrivateProfileString strSection, _
   strKey, strValue, strInI
End Sub
 
Public Function GetFile(strSection As String, _
  strKey As String) As String
 
  Dim strTmp As String
  Dim lngRet As String
 
  strTmp = String$(100, 0)
  lngRet = GetPrivateProfileString(strSection, _
    strKey, "", strTmp, _
    Len(strTmp), strInI)
 
  GetFile = StrZ(strTmp)
 
End Function
 
Public Property Let INIFile(ByVal New_IniPath As String)
   'Устанавливаем путь к файлу ini
   strInI = New_IniPath
End Property
Public Property Get INIFile() As String
   INIFile = strInI
End Property
 
 
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "FormNastroyka"
Attribute VB_Base = "0{51A1FE8F-F53E-4A77-991A-F9C8A7DC8110}{7922693B-686E-4C86-95E5-01FAB5230B49}"
Attribute VB_GlobalNameSpace = False
Attribute VB_Creatable = False
Attribute VB_PredeclaredId = True
Attribute VB_Exposed = False
Attribute VB_TemplateDerived = False
Attribute VB_Customizable = False
Option Explicit

Private Sub UserForm_Click()

End Sub

Attribute VB_Name = "FormVyborBibl"
Attribute VB_Base = "0{E12AEB80-3B6F-465F-A76D-C565F1060B78}{7F5D9A82-95E9-4829-B55D-66A5441538BA}"
Attribute VB_GlobalNameSpace = False
Attribute VB_Creatable = False
Attribute VB_PredeclaredId = True
Attribute VB_Exposed = False
Attribute VB_TemplateDerived = False
Attribute VB_Customizable = False
Option Explicit
      
   Enum DelOrReplace
      Delete = 0
      Replace = 1
   End Enum
   
'   'aFilesDubl.Path - тут будет дублирующийся файл
'   'aFilesDubl.FilesDwg - пути к этому файлу
'   'aFilesDubl.IsFiles - что есть пути
   Dim bolFilesDublic As Boolean
      
   
Private Sub cmbBiblAdd_Click()
   'добавить имя библиотеки в форму и в ини и сделать ее выделенной
   
   FormaAddBibl.show
      
End Sub

Private Sub cmbBiblDelete_Click()
   'удалить выбранную библиотеку
   
   Dim strBiblForDelete As String
   Dim strValue As String
   Dim intOtvet As Integer
   Dim i As Integer
   Dim j As Integer
   
   'определяем выделенную библиотеку для удаления
   If ListBoxBiblName.ListCount = 0 Then
      MsgBox "Не выбрана библиотека для ее удаления!"
      Exit Sub
   End If
   strBiblForDelete = ListBoxBiblName.Text
   'запрос подтверждения удаления
   intOtvet = MsgBox("Вы деуствительно хотите удалить библиотеку - " & strBiblForDelete, vbYesNo, "Удаление библиотеки " & strBiblForDelete)
   If intOtvet = 7 Then 'нет
      Exit Sub
   End If
   'удаляем библиотеку из листбокса, из массива,и если она была текущей тоже удаляем
   'из листбокса
   i = ListBoxBiblName.ListIndex
   ListBoxBiblName.RemoveItem i
   'удаляем имя библиотеки из массива
   For i = 0 To UBound(Bibles)
      If Bibles(i).Name = strBiblForDelete Then
         Bibles(i).Name = ""
         'удаление пустых имен в библиотеке
         BiblNamesRefresh i
         Exit For
      End If
   Next
   
   'если удаляемая библиотека была текущей становленной
   If LabelCurBiblName = strBiblForDelete Then
      LabelCurBiblName = ""
   End If
   
End Sub

Private Sub cmbBiblRename_Click()
   'запросить новое имя для библиотеки
   Dim strNewBiblName As String
   Dim strOldBiblName As String
   Dim strKeyForBiblName As String
   Dim i As Integer
   
   If ListBoxBiblName.ListCount = 0 Then
      MsgBox "Не выбана библиотека для переименования!"
      Exit Sub
   End If
   strOldBiblName = ListBoxBiblName.Text
   FormaBiblRename.TextBoxBiblName = strOldBiblName
   FormaBiblRename.show
   strNewBiblName = FormaBiblRename.TextBoxBiblName.Text
   'проверяем, пустая строка или нет
   If Len(strNewBiblName) = 0 Then
      'пустая строка, выходим из процедры, без изменений
      Exit Sub
   End If
   'проверяем изменилось ли имя
   If Not StrComp(strOldBiblName, strNewBiblName, vbTextCompare) = 0 Then 'переименвываем
      'переименовываем имя в массиве имен библиотек
      For i = 0 To UBound(Bibles)
         If Bibles(i).Name = strOldBiblName Then
            Bibles(i).Name = strNewBiblName
            Exit For
         End If
      Next
      'переименовываем имя библиотеки в этой форме в листбоксе имен библиотек
      For i = 0 To ListBoxBiblName.ListCount
         If ListBoxBiblName.List(i, 0) = strOldBiblName Then
            ListBoxBiblName.List(i, 0) = strNewBiblName
            Exit For
         End If
      Next
      'если в названии текущей иблиотеки было strOldBiblName, то переименовываем
      If LabelCurBiblName = strOldBiblName Then
         LabelCurBiblName = strNewBiblName
      End If
   End If
   
End Sub

Private Sub cmbBiblSet_Click()
   'записываем выделенную библиотеку как текущую в ини при условии наличия путей
   'записываем имя текущей библиотеки в текстбокс формы
   
   Dim strBible As String
   
   'если нет библиотек
   If ListBoxBiblName.ListCount = 0 Then
      MsgBox "Библиотек нет!" & vbCrLf _
            & "Создайте библиотеку!"
      Exit Sub
   End If
   
   strBible = ListBoxBiblName.Text
   
   'нельзя установит типовую
   If strBible = strStandartBiblName Then
      MsgBox "Типовую библиотеку нельзя установит текущей!"
      Exit Sub
   End If
         
   'текстбокс меняем
   LabelCurBiblName = strBible
   
   'Записываем в ини
   FileIni.WriteFile strSectionOther, strKeyCurrentBibl, strBible
   
End Sub

Private Sub cmbExit_Click()
   
   FormaExit.show
   
'   If bolExit = True Then
'      hide
'   End If
   
End Sub

Private Sub cmbLoad_Click()
   'т.е. считываем данные из ини
   
   'считываем ини в массив библиотек Bibles
   ReadINI
   'заполняем форму из Bibles
   WriteBiblesToForm
   
End Sub

Private Sub cmbOK_Click()
   'проверим есть ли хоть один путь для текущей библиотеки
   
   Dim strCurBibleName As String
   Dim i As Integer
   Dim j As Integer
   Dim intOtvet As Integer
   Dim asFiles() As String
'   Dim sMsg As String
'   Dim bolHasNotExistsFolders As Boolean
   
   If bolBiblIs = False Then
      'библиотек нет
      MsgBox "Создайте библиотеку!"
      Exit Sub
   End If
   
   strCurBibleName = LabelCurBiblName
   
   If Len(strCurBibleName) <> 0 Then
      For i = 0 To UBound(Bibles)
         If Bibles(i).Name = strCurBibleName Then
            If Bibles(i).IsPathes = False Then
               MsgBox "Для текущей библиотеке не установлен ни один путь!"
               Exit Sub
            Else
               'проверка доступности путей, если хоть один путь недоступен, то продолжать нельзя.
               If CheckExistsAllFolderInLib(Bibles(i).Paths) = False Then
                  'есть недоступные пути. нельзя продолжать
                  Exit Sub
               End If
'               sMsg = "Недоступные пути в библиотеке " & LabelCurBiblName & ". Проверьте доступность папок:" & vbCrLf & vbCrLf
'               bolHasNotExistsFolders = False
'               For j = 0 To UBound(Bibles(i).Paths)
'                  If FolderExists(Bibles(i).Paths(j).path) = False Then
'                    sMsg = sMsg & Bibles(i).Paths(j).path & vbCrLf
'                    bolHasNotExistsFolders = True
'                  End If
'               Next
'               If bolHasNotExistsFolders = True Then
'                  MsgBox sMsg, vbCritical
'                  Exit Sub
'               End If
               
               'подтверждение выбранной библиотеки
               intOtvet = MsgBox("Установленна библиотека - " & strCurBibleName, vbYesNo)
               If intOtvet = 7 Then
                  Exit Sub
               End If
               'получаем файлы dwg для всех путей
               For j = 0 To UBound(Bibles(i).Paths)
                  'получаем массив строк имен файлов dwg
                  asFiles = SearchFileInFileSystem(Bibles(i).Paths(j).path)
                  If asFiles(0) = "" Or asFiles(0) = "0" Then
                     'нет папки или нет dwg
                     Bibles(i).Paths(j).IsFiles = False
                     Erase Bibles(i).Paths(j).FilesDwg
                  Else
                     Bibles(i).Paths(j).IsFiles = True
                     Bibles(i).Paths(j).FilesDwg = asFiles
                  End If
               Next
            End If
         End If
      Next
   Else
      'не установлена текущая библиотека
      MsgBox "Установите текущую библиотеку!"
      Exit Sub
   End If
   
   'заполняем файлы типовой библиотеки
   If StandartBibl.IsPathes = True Then
      For i = 0 To UBound(StandartBibl.Paths)
         'получаем массив строк имен файлов dwg
         asFiles = SearchFileInFileSystem(StandartBibl.Paths(i).path)
         If asFiles(0) = "" Or asFiles(0) = "0" Then
            'нет папки или нет dwg
            StandartBibl.Paths(i).IsFiles = False
            Erase StandartBibl.Paths(i).FilesDwg
         Else
            StandartBibl.Paths(i).IsFiles = True
            StandartBibl.Paths(i).FilesDwg = asFiles
         End If
      Next
   End If
   
   'запрос подтверждения текущей библы и путей
'   FormaCurBibl

   'сохранение библиотек в ини
   cmbSaveChanges_Click
   
   ListBoxBiblName.Clear
   ListBoxFiles.Clear
   ListBoxPath.Clear
   
   hide

End Sub

Private Sub cmbPathAdd_Click()
   'добавление пути к выделенной в листбоксебибл библеотеке
   
   Dim strBiblName As String
   Dim strPathToAdd As String
   Dim strPathDefault As String
   Dim i As Integer
   Dim j As Integer
   Dim bolYes As Boolean
   Dim asFilesDwdTemp() As String
   
   On Error GoTo HasError

   'определяем выделенную библиотеку в ListBoxBiblName, для нее и будем добавлять путь
   If ListBoxBiblName.ListCount = 0 Then
      MsgBox "Не выбрана библиотека для которой нужно добавить каталог."
      Exit Sub
   End If
   strBiblName = ListBoxBiblName.Text
      'задаем путь для первого пути в этой библиотеке
      If ListBoxPath.ListCount <> 0 Then 'если есть пути
         'выбираем выделенный или первый по списку
         If Len(ListBoxPath.Text) <> 0 Then 'если не выделен?????кажется не правильная проверка, надо через листиндекс=-1
            strPathDefault = ListBoxPath.Text
         Else
            'выбираем первый из путей
            strPathDefault = ListBoxPath.List(0, 0)
         End If
      Else 'если в листбоксе нет путей
         'определяем путь по умолчанию, из ини
         strPathDefault = FileIni.GetFile(strSectionOther, strKeyForPathDefault)
         If strPathDefault = "" Then
            'задаем путь к текущему чертежу
            strPathDefault = ThisDrawing.path
         End If
      End If
      
   'открываем диалог выбора папок
   strPathToAdd = BrowseDialog.FolderBrowse("Внимание: вложенные папки не учиываются.", strPathDefault)
   RemoveSlashAtEndOfPathFolder strPathToAdd
'    strPathToAdd = fBrowseForFolder(hWnd_Owner:=0&, _
                          sPrompt:="Внимание: вложенные папки не учиываются." & vbCrLf & _
                                    "Поэтому выбирайте каждый каталог по отдельности.", _
                          WhatBr:=BIF_RETURNONLYFSDIRS Or BIF_STATUSTEXT, _
                          DialogTitle:="Выберите папку c блоками (с файлами dwg)", _
                          initDir:=strPathDefault, _
                          fileMasks:="", _
                          ChangeSize:=True, _
                          RatioX:=1, _
                          RatioY:=1, _
                          CenterOnScreen:=True, _
                          TopMost:=True)
    'fileMasks:="*.DWG|*.TIF" - пример для фильтра типов файлов
   If Len(strPathToAdd) = 0 Then 'если не выбрана папка
      Exit Sub
   End If
   
   'для типовой библиотеки
   If strBiblName = strStandartBiblName Then
      
      'Добавлено 27.10.09
      'проверяем не серииный ли путь пытаются добавить в типовую библиотеку ???????????
      If bolBiblIs = True Then
        For i = 0 To UBound(Bibles)
          If Bibles(i).IsPathes = True Then
              For j = 0 To UBound(Bibles(i).Paths)
                  If Bibles(i).Paths(j).path = strPathToAdd Then
                      MsgBox "Такой путь уже есть в библиотеке - " & Bibles(i).Name
                      Exit Sub
                  End If
              Next
          End If
        Next
      End If
    
      If StandartBibl.IsPathes = True Then
         'проверяем нет ли там уже такого пути
         bolYes = False 'входное значене
         For i = 0 To UBound(StandartBibl.Paths)
            If StandartBibl.Paths(i).path = strPathToAdd Then
               bolYes = True 'типа есть такой путь
               MsgBox "Такой путь уже есть в этой библиотеке!"
            End If
         Next
         If bolYes = False Then
            j = UBound(StandartBibl.Paths) + 1
            ReDim Preserve StandartBibl.Paths(j)
            StandartBibl.Paths(j).path = strPathToAdd
'            'записываем массив файлов в этом пути
'            asFilesDwdTemp = MakeArrayFilesDWGFromPath(strPathToAdd)
'            If asFilesDwdTemp(0) <> "" And asFilesDwdTemp(0) <> "0" Then
'               StandartBibl.Paths(j).FilesDwg = asFilesDwdTemp
'               Erase asFilesDwdTemp
'               StandartBibl.Paths(j).IsFiles = True
'            End If
            'добавляем путь в листбокс
            ListBoxPath.AddItem strPathToAdd
         End If
      Else 'нет путей у типовой библ
         ReDim Preserve StandartBibl.Paths(0)
         StandartBibl.Paths(0).path = strPathToAdd
         StandartBibl.IsPathes = True
'         'записываем массив файлов в этом пути
'         asFilesDwdTemp = MakeArrayFilesDWGFromPath(strPathToAdd)
'         If asFilesDwdTemp(0) <> "" And asFilesDwdTemp(0) <> "0" Then
'            StandartBibl.Paths(0).FilesDwg = asFilesDwdTemp
'            Erase asFilesDwdTemp
'            StandartBibl.Paths(0).IsFiles = True
'         End If
'         StandartBibl.Paths(0).IsFiles = True
         'добавляем путь в листбокс
         ListBoxPath.AddItem strPathToAdd
      End If
      
   Else 'для не типовой библиотеки перебираем массив библиотек
   
      'Добавлено 27.10.09
      'проверяем не типовой лит путь пытаются добавить в типовую библиотеку ????????
      If StandartBibl.IsPathes = True Then
        For i = 0 To UBound(StandartBibl.Paths)
         If StandartBibl.Paths(i).path = strPathToAdd Then
            'не нужно добавлять в сеирию пути которые уже есть в типовой библе
            MsgBox "Такой путь уже есть в Типовой библиотеке!"
            Exit Sub
         End If
        Next
      End If
        
      'добавляем путь в листбокс и массив если еще такого пути там нет
      For i = 0 To UBound(Bibles)
         If Bibles(i).Name = strBiblName Then
            If Bibles(i).IsPathes = True Then
               'проверяем нет ли уже такого пути
               bolYes = False 'входное значеие
               For j = 0 To UBound(Bibles(i).Paths)
                  If Bibles(i).Paths(j).path = strPathToAdd Then
                     bolYes = True 'есть такой путь
                     MsgBox "Такой путь уже есть в этой библиотеке!"
                  End If
               Next
               If bolYes = False Then 'если такого пути нет, то добавляем его
                  j = UBound(Bibles(i).Paths) + 1
                  ReDim Preserve Bibles(i).Paths(j)
                  Bibles(i).Paths(j).path = strPathToAdd
'                  'записываем массив файлов в этом пути
'                  asFilesDwdTemp = MakeArrayFilesDWGFromPath(strPathToAdd)
'                  If asFilesDwdTemp(0) <> "" And asFilesDwdTemp(0) <> "0" Then
'                     Bibles(i).Paths(j).FilesDwg = asFilesDwdTemp
'                     Erase asFilesDwdTemp
'                     Bibles(i).Paths(j).IsFiles = True
'                  End If
                  'добавляем путь в листбокс
                  ListBoxPath.AddItem strPathToAdd
               End If
            Else 'если в библиотеке нет путей
               ReDim Bibles(i).Paths(0)
               Bibles(i).Paths(0).path = strPathToAdd
               Bibles(i).IsPathes = True
'               'записываем массив файлов в этом пути
'                  asFilesDwdTemp = MakeArrayFilesDWGFromPath(strPathToAdd)
'                  If asFilesDwdTemp(0) <> "" And asFilesDwdTemp(0) <> "0" Then
'                     Bibles(i).Paths(0).FilesDwg = asFilesDwdTemp
'                     Erase asFilesDwdTemp
'                     Bibles(i).Paths(0).IsFiles = True
'                  End If
               'добавляем путь в листбокс
               ListBoxPath.AddItem strPathToAdd
            End If
            Exit For
         End If
      Next
   End If 'strBiblName = strStandartBiblName
   
   'записываем путь в ини
   FileIni.WriteFile strSectionOther, strKeyForPathDefault, strPathToAdd
   
Exit Sub
HasError:
   MsgBox Err.Description, vbCritical
   
End Sub

Private Sub cmbPathDelete_Click()
   'удалить выбранный путь из листбокса путей и из массива библиотек
   
   Dim strBiblName As String
   Dim strPathToDel As String
   Dim strValue As String
   Dim intIndex As Integer
   Dim intOtvet As Integer
   Dim i As Integer
   Dim j As Integer
   
   'удаляемый путь
   If ListBoxPath.ListCount = 0 Then
      MsgBox "Не выделен путь который нужно удалить."
      Exit Sub
   End If
   strPathToDel = ListBoxPath.Text
   'определяем выделенную библиотеку в ListBoxBiblName
   strBiblName = ListBoxBiblName.Text
   
   'запрос подтверждения удаления пути
   intOtvet = MsgBox("Вы действительно хотите удалить путь - " & vbCrLf & _
                  strPathToDel & vbCrLf & _
                  "Из библиотеки - " & strBiblName, vbYesNo)
   If intOtvet = 7 Then
      Exit Sub
   End If
   'удаляем из листбокса
   intIndex = ListBoxPath.ListIndex
   ListBoxPath.RemoveItem intIndex
   'удаляем библиотеку из массива
   If strBiblName = strStandartBiblName Then
      'из типовой библ
      For i = 0 To UBound(StandartBibl.Paths)
         If StandartBibl.Paths(i).path = strPathToDel Then
            StandartBibl.Paths(i).path = ""
            'перепись массива путей без указанного номера
            BiblPathRefresh StandartBibl, i
            Exit For
         End If
      Next
   Else 'не типовая библиотека
      'удаляем путь из маасива библиотек
      For i = 0 To UBound(Bibles)
         If Bibles(i).Name = strBiblName Then
            For j = 0 To UBound(Bibles(i).Paths) '????не уверен
               If Bibles(i).Paths(j).path = strPathToDel Then
                  Bibles(i).Paths(j).path = ""
                  'перепись массива путей без указанного номера
                  BiblPathRefresh Bibles(i), j
                  Exit For
               End If
            Next
         End If
      Next
   End If 'strBiblName = strStandartBiblName
      
End Sub


Private Sub cmbProvDubl_Click()
   
   'проверка дубликатов файлов в библиотеке
   'вместе с типовой
   'вывод результатов в отдельной форме
   
   Dim strBibl As String
   Dim aPath() As path
   Dim asFiles() As String
   Dim i As Integer
   Dim j As Integer
   Dim k As Integer
   Dim l As Integer
   Dim m As Integer
   
   'очищаем массив
   Erase aFilesDubl
   bolFilesDublic = False
   
   'находим библу
   strBibl = ListBoxBiblName.Text
   If strBibl = strStandartBiblName Then
      aPath = StandartBibl.Paths
   Else
      For i = 0 To UBound(Bibles)
         If Bibles(i).Name = strBibl Then
            If Bibles(i).IsPathes = True Then
               aPath = Bibles(i).Paths
               Exit For
            Else
               MsgBox "Путей нет!"
               Exit Sub
            End If
         End If
      Next
   End If
   
   If UBound(aPath) = 0 Then
      MsgBox "Дубликатов быть не может, т.к. в библиотеке только один путь!"
      Exit Sub
   End If
   
   'проверка доступности всех путей в библиотеке
   If CheckExistsAllFolderInLib(aPath) = False Then
      Exit Sub
   End If
   
   'заполняем массивы файлов для каждого пути библы
   For i = 0 To UBound(aPath)
      'процедура получения списка файлов в папке, на данный момент времени
      asFiles = SearchFileInFileSystem(aPath(i).path)
      If asFiles(0) = "" Or asFiles(0) = "0" Then
         'нет папки или нет dwg
         aPath(i).IsFiles = False
         Erase aPath(i).FilesDwg
      Else
         aPath(i).IsFiles = True
         aPath(i).FilesDwg = asFiles
      End If
   Next
   
   Erase asFiles
   
   
   'перебираем все пути выбранной библиотеки
   'проверяем совпадение имен файлов
   For i = 0 To UBound(aPath) - 1
      
      If aPath(i).IsFiles = True Then
         For j = 0 To UBound(aPath(i).FilesDwg)
            'перебироем остальные пути этой библы
            For k = i + 1 To UBound(aPath)
               
             If aPath(k).IsFiles = True Then
               For l = 0 To UBound(aPath(k).FilesDwg)
                  
                  If StrComp(aPath(i).FilesDwg(j), aPath(k).FilesDwg(l), vbTextCompare) = 0 Then
                     'процедура добавления путей и файла в дубликаты
                     AddDublic aPath(i).FilesDwg(j), aPath(i).path, aPath(k).path
                  End If
               Next
             End If
            Next
            'проверяем дубликаты этого файла в типовой библе
            If strBibl <> strStandartBiblName Then
               DublBiblFileInStandard aPath(i).FilesDwg(j), aPath(i).path
            End If
         Next
      End If
   Next
   
   If bolFilesDublic = True Then
      'есть дубликаты
      'выводим их в форму
      FormaDublic.show
   Else
      'нет дубликатов
      MsgBox "Дубликатов нет!"
   End If
   
End Sub

Private Sub cmbSaveChanges_Click()
   'записываем массив библиотек в ини
   
   Dim i As Integer
   Dim j As Integer
   Dim intNumBiblName As Integer
   Dim intNumBiblPath As Integer
   Dim strPathDef As String
   
   On Error GoTo HasError

   'считываем путь для поиска
   strPathDef = FileIni.GetFile(strSectionOther, strKeyForPathDefault)
   
   'удаляем ини файл
   If Len(Dir(strMacroPath & "\Ini\" & strFileIniName)) <> 0 Then 'если есть ини файл
      'удаляем его
      Kill strMacroPath & "\Ini\" & strFileIniName
   End If
   'создаем ини файл
   FileIni.CreateIni strFileIniName, strMacroPath & "\Ini"
   'записываем имена библиотек и их пути
   If bolBiblIs = True Then
      intNumBiblName = 0 'входящие значения
      For i = 0 To UBound(Bibles)
         If Len(Bibles(i).Name) <> 0 Then
            FileIni.WriteFile strSectionBibl, CStr(intNumBiblName), Bibles(i).Name
            If Bibles(i).IsPathes = True Then
               intNumBiblPath = 0 'входящие значения
               For j = 0 To UBound(Bibles(i).Paths)
                  If Len(Bibles(i).Paths(j).path) <> 0 Then
                     FileIni.WriteFile Bibles(i).Name, CStr(intNumBiblPath), Bibles(i).Paths(j).path
                     intNumBiblPath = intNumBiblPath + 1
                  End If
               Next
            End If 'Bibles(i).IsPathes = True
            intNumBiblName = intNumBiblName + 1
         End If
      Next
      'сохранием текущую библиотеку
      FileIni.WriteFile strSectionOther, strKeyCurrentBibl, LabelCurBiblName
   End If 'bolBiblIs = True
   
   'сохраняем пути для типовой библы
      intNumBiblPath = 0 'входящее значение
      If StandartBibl.IsPathes = True Then
         For i = 0 To UBound(StandartBibl.Paths)
            If Len(StandartBibl.Paths(i).path) <> 0 Then
               FileIni.WriteFile strStandartBiblName, CStr(intNumBiblPath), StandartBibl.Paths(i).path
               intNumBiblPath = intNumBiblPath + 1
            End If
         Next
      End If
   
   'нужно сохранить путь поиска папки
   If Len(strPathDef) <> 0 Then
      FileIni.WriteFile strSectionOther, strKeyForPathDefault, strPathDef
   End If

Exit Sub
HasError:
   MsgBox Err.Description, vbCritical
   
End Sub


Private Sub ListBoxBiblName_Change()
   'при выделении библиотеке отображать пути для нее
      
   PathsForBiblSelected
   
   'делать библу текущей
   
   Dim strBible As String
   
   'если нет библиотек
   If ListBoxBiblName.ListCount = 0 Then
      Exit Sub
   End If
   
   strBible = ListBoxBiblName.Text
   
   'нельзя установит типовую
   If strBible = strStandartBiblName Then
      Exit Sub
   End If
         
   'текстбокс меняем
   LabelCurBiblName = strBible
   
End Sub

Private Sub ListBoxBiblName_DblClick(ByVal Cancel As MSForms.ReturnBoolean)
   'установка библиотеки, как на кнопке Установить
   cmbBiblSet_Click
End Sub

Private Sub ListBoxPath_Change()
   
   'вывод списка файлов в папке
   
   Dim strPath As String
   Dim strBibl As String
   Dim strValue As String
   Dim i As Integer
   Dim j As Integer
   Dim asFiles() As String
   Dim bolYes As Boolean
   
   
   On Error GoTo HasError
   
   
   strBibl = ListBoxBiblName.Text
   strPath = ListBoxPath.Text
   If strPath = "" Then
      Exit Sub
   End If
   
   ListBoxFiles.Clear
   LabelFiles = "Список файлов dwg:"
   
   'проверка доступности пути
   strValue = Dir(strPath, vbDirectory) 'должны получить имя этой папки или "" если ее нет
   If strValue = "" Then
      MsgBox "Путь недоступен! Проверьте путь к папке.", vbExclamation
      Exit Sub
   End If
   
   'если выбрана типовая библа
   If strBibl = strStandartBiblName Then
      For i = 0 To UBound(StandartBibl.Paths)
         If StandartBibl.Paths(i).path = strPath Then
            'процедура получения списка файлов в папке из FileSystem, на данный момент времени
            asFiles = SearchFileInFileSystem(strPath)
               If asFiles(0) = "" Or asFiles(0) = "0" Then
                  'нет папки или нет dwg
                  StandartBibl.Paths(i).IsFiles = False
                  Erase StandartBibl.Paths(i).FilesDwg
                  bolYes = False
               Else
                  StandartBibl.Paths(i).IsFiles = True
                  StandartBibl.Paths(i).FilesDwg = asFiles
                  bolYes = True
                  Exit For
               End If
         End If
      Next
      
   Else 'не типовая библа
   
      'находим библу
      For i = 0 To UBound(Bibles)
         If Bibles(i).Name = strBibl Then
            For j = 0 To UBound(Bibles(i).Paths)
               If Bibles(i).Paths(j).path = strPath Then
                  'процедура получения списка файлов в папке из FileSystem, на данный момент времени
                  asFiles = SearchFileInFileSystem(strPath)
                  If asFiles(0) = "" Or asFiles(0) = "0" Then
                     'нет папки или нет dwg
                     Bibles(i).Paths(j).IsFiles = False
                     Erase Bibles(i).Paths(j).FilesDwg
                     bolYes = False
                  Else
                     Bibles(i).Paths(j).IsFiles = True
                     Bibles(i).Paths(j).FilesDwg = asFiles
                     bolYes = True
                     Exit For
                  End If
               End If
            Next
         End If
      Next
      
   End If
   
   If bolYes = True Then
      ListBoxFiles.List = asFiles '??????????не уверен
      LabelFiles = "Список файлов dwg: " & UBound(asFiles) + 1
   End If
   
Exit Sub
HasError:
   If Err.Number = 52 Then Resume Next
   MsgBox Err.Description, vbCritical
   
End Sub

Private Sub ListBoxPath_Click()
   'если выбан путь, то подсвечиваем кнопку удаления пути
   
   If Len(ListBoxPath.Text) <> 0 Then
      cmbPathDelete.Enabled = True
      'TextBoxSelectPath = ListBoxPath.Text
   End If
   
End Sub

Private Sub UserForm_Activate()
   'считываем инфу из ини
   
   Dim strMacroFullPath As String
   Dim intValue As Integer
   
   On Error GoTo HasError
   
   ListBoxBiblName.Clear
   ListBoxFiles.Clear
   ListBoxPath.Clear
   
   'определяем путь к макросу
   strMacroFullPath = AutoCAD.Application.VBE.VBProjects.Item("ZB").FileName
   intValue = InStrRev(strMacroFullPath, "\")
   strMacroPath = Left$(strMacroFullPath, intValue - 1) 'без "\"
   
   'создаем ини файл (т.е. связываем класс с существующим ини файлом)
   FileIni.CreateIni strFileIniName, strMacroPath & "\Ini"
   
   'запсываем в массив все имена библиотек и пути в массив библиотек типа Bibles()
   ReadINI
   
   'заполняем форму
   WriteBiblesToForm
   
   'скрываем кнопки установить, переиеменовать, удалить, если нет ни одной бибиотеки
   If Len(ListBoxBiblName.Text) = 0 Then
      cmbBiblDelete.Enabled = False
      cmbBiblRename.Enabled = False
      cmbBiblSet.Enabled = False
   End If
   'скрываем кнопку удалить путь если не выделен путь
   If Len(ListBoxPath.Text) = 0 Then
      cmbPathDelete.Enabled = False
   End If

Exit Sub
HasError:
   MsgBox Err.Description, vbCritical
   
End Sub

Private Sub UserForm_QueryClose(Cancel As Integer, CloseMode As Integer)
   FormaExit.show
End Sub

Private Sub PathsForBiblSelected()
   'отображение путей в ListBoxBiblName для указанной библиотеки
   
   Dim strBiblName As String
   Dim i As Integer
   Dim j As Integer
   
   'очищаем список путей
   ListBoxPath.Clear
   
   strBiblName = ListBoxBiblName.Text
   
   'если это типовая библиотека
   If strBiblName = strStandartBiblName Then
      If StandartBibl.IsPathes = True Then
         For i = 0 To UBound(StandartBibl.Paths)
            If Len(StandartBibl.Paths(i).path) <> 0 Then
               ListBoxPath.AddItem StandartBibl.Paths(i).path
            End If
         Next
      End If
      cmbBiblDelete.Enabled = False
      cmbBiblRename.Enabled = False
      cmbBiblSet.Enabled = False
   Else
      'находим библиотеку по имени
      For i = 0 To UBound(Bibles)
         If Bibles(i).Name = strBiblName Then
            'заполняем листбокс ListBoxPath, если есть пути в ассиве
            If Bibles(i).IsPathes = True Then
               For j = 0 To UBound(Bibles(i).Paths)
                  If Len(Bibles(i).Paths(j).path) <> 0 Then
                     ListBoxPath.AddItem Bibles(i).Paths(j).path
                  End If
               Next
            End If 'Bibles(i).IsPathes = True
            Exit For
         End If
      Next
      cmbBiblDelete.Enabled = True
      cmbBiblRename.Enabled = True
      cmbBiblSet.Enabled = True
   End If 'strBiblName = strStandartBiblName
   
   'в Frame путей записываем имя выбранной библиотеки
   Frame1.Caption = "Пути для выбранной библиотеки: " & strBiblName
   
End Sub

'Private Function FindKeyForBiblName(BiblName As String) As String
'   'в ини находим заданную библиотеку и возвращаем ключ для неё
'   Dim bolYes As Boolean
'   Dim strValue As String
'   Dim i As Integer
'
'   While bolYes = False
'      strValue = FileIni.GetFile(strSectionBibl, i)
'      If strValue = BiblName Then 'нашлась
'         FindKeyForBiblName = i
'         bolYes = True
'      End If
'      i = i + 1
'   Wend
'
'End Function

'Private Sub FindStringInIniAnd(StringForSearch As String, DelOrReplace As Integer, Optional StringForReplace As String)
'   'процедура удаления/замены строчки в ини файле
'   Dim strPathToIni As String
'   Dim strValue As String
'   Dim bolYes As Boolean
'   Dim objFS As New FileSystemObject
'   Dim objFile As TextStream
'   Dim strTemp As String
'
'   'получаем путь к ини файлу
'   strPathToIni = FileIni.INIFile
'   'открываем его для редактирование и считываем весь файл в strTemp
'   Set objFile = objFS.OpenTextFile(strPathToIni, ForReading)
'   strTemp = objFile.ReadAll
'   objFile.Close
'   If DelOrReplace = 0 Then 'удалить строчку(и)
'      strTemp = VBA.Replace(strTemp, StringForSearch, "", 1, -1, vbTextCompare)
'   ElseIf DelOrReplace = 1 Then 'заменить строчку(и)
'      strTemp = VBA.Replace(strTemp, StringForSearch, StringForReplace, 1, -1, vbTextCompare)
'   End If
'   Set objFile = objFS.OpenTextFile(strPathToIni, 2, True)
'   objFile.Write strTemp
'   objFile.Close
'
'End Sub

Private Sub ReadINI()
   'чтение ини файла, всех библиотек и их путей в массив типа Bibles
   'и проверка дубликатов полученых имен
   'при этом в ини ничего не исправляется
   
   Dim BiblesCopy() As Bibl
   Dim strArrayTemp() As String  'временный массив для ускорения работы и проверок
   Dim strValue As String
   Dim strBiblName As String
   Dim strPath As String
   Dim i As Integer
   Dim j As Integer
   Dim k As Integer
   Dim intOtvet As Integer
   Dim bolYes As Boolean
   Dim bolPathIs As Boolean
   Dim asFilesDwdTemp() As String
   
   On Error GoTo HasError

   'ститываем пути для типовой библиотеки
'   Set StandartBibl = Nothing 'очищаем массв путей типовой библиотеки
   i = 0 'входное значение
   Do
      'считываем путь типовой библиотек
      strPath = FileIni.GetFile(strSectionStandartBibl, CStr(i))
      If Len(strPath) <> 0 Then
         strPath = SearchPath(strPath, strStandartBiblName)
         If Len(strPath) <> 0 Then
            'проверяем не дублируются ли пути
            If i > 0 Then 'если в массиве больше 1 пути
               bolYes = False
               For j = 0 To UBound(StandartBibl.Paths)
                  If StandartBibl.Paths(j).path = strPath Then
                     bolYes = True 'типа уже есть такой путь
                     Exit For
                  End If
               Next
            End If
            If bolYes = False Then
               ReDim Preserve StandartBibl.Paths(i)
               StandartBibl.Paths(i).path = strPath
               StandartBibl.IsPathes = True
'               'заполняем массив имен файлов dwg для этого пути
'               asFilesDwdTemp = MakeArrayFilesDWGFromPath(strPath)
'               If asFilesDwdTemp(0) <> "" And asFilesDwdTemp(0) <> "0" Then
'                  StandartBibl.Paths(i).FilesDwg = asFilesDwdTemp
'                  Erase asFilesDwdTemp
'                  StandartBibl.Paths(i).IsFiles = True
'               End If
'               bolStandarBiblIs = True'уже есть StandartBibl.IsPathes
               i = i + 1 'счетчик определенных путей
            End If
         End If 'Len(strPath) <> 0
      End If
   Loop Until Len(strPath) = 0
   
   
   'считываем имена библиотек
   'в ини файле не должно быть пустых имен библиотек, поэтому читаем до первой пустой полученной строки
   'тоже самое касается и путей
   i = 0 'входное значение
   Do
      'считываем из ини имя библиотеки, по номеру
      strValue = FileIni.GetFile(strSectionBibl, CStr(i))
      If Len(strValue) <> 0 Then
         'проверяем, если имя библиотеки = типовая
         If Not StrComp(strValue, strStandartBiblName, vbTextCompare) = 0 Then
            'проверяем нет ли уже такой библиотеки
            If i > 0 Then 'если в массиве больше 1 имени
               bolYes = False
               For j = 0 To UBound(strArrayTemp)
                  If strArrayTemp(j) = strValue Then
                     bolYes = True 'типа уже есть такая библа
                     Exit For
                  End If
               Next
            End If
            If bolYes = False Then 'нет такой библы, добавляем
               ReDim Preserve strArrayTemp(i)
               strArrayTemp(i) = strValue 'массив имен библиотек
               i = i + 1
               bolBiblIs = True
            End If
         End If
      End If
   Loop Until Len(strValue) = 0
   'проверяем создан ли массив, т.е. найдена ли хоть одна библиотека
   If bolBiblIs = False Then
      'в ини нет библиотек
      Exit Sub
   End If
   'передаем имена в головной массив библиотек
      ReDim Bibles(UBound(strArrayTemp))
      For i = 0 To UBound(strArrayTemp)
         Bibles(i).Name = strArrayTemp(i)
      Next
      Erase strArrayTemp
   
   'для каждой библиотеки считываем пути из ини и по ходу проверяем дубликаты путей
   For i = 0 To UBound(Bibles)
      strBiblName = Bibles(i).Name
      j = 0 'входное значение, ключ для 1 пути в ини
      bolPathIs = False 'входное значение
      Do
         'получаем пути для секции = имени библиотеки
         strPath = FileIni.GetFile(strBiblName, CStr(j))
         If Len(strPath) <> 0 Then 'есть какое то значение
            strPath = SearchPath(strPath, strBiblName)
            If Len(strPath) <> 0 Then
               'проверяем нет ли уже такого пути
               If j > 0 Then 'если в массиве больше 1 пути
                  bolYes = False
                  For k = 0 To UBound(strArrayTemp)
                     If strArrayTemp(k) = strPath Then
                        bolYes = True 'типа уже есть такой путь
                        Exit For
                     End If
                  Next
               End If
               If bolYes = False Then 'нет такого пути, добавляем
                  ReDim Preserve strArrayTemp(j) As String
                  strArrayTemp(j) = strPath
                  bolPathIs = True
                  j = j + 1
               End If
            End If
         End If 'strPath <> ""
      Loop Until Len(strPath) = 0
      'заносим найенные рути в массив Bibles
      If bolPathIs = True Then 'если есть пути
         ReDim Bibles(i).Paths(UBound(strArrayTemp)) '????? неуверен, протестировать
         Bibles(i).IsPathes = True
         For j = 0 To UBound(strArrayTemp)
            Bibles(i).Paths(j).path = strArrayTemp(j)  '?????не уверен
'            'заполняем массив имен файлов dwg для этого пути
'            asFilesDwdTemp = MakeArrayFilesDWGFromPath(strArrayTemp(j))
'            If asFilesDwdTemp(0) <> "" And asFilesDwdTemp(0) <> "0" Then
'               Bibles(i).Paths(j).FilesDwg = asFilesDwdTemp
'               Erase asFilesDwdTemp
'               Bibles(i).Paths(j).IsFiles = True
'            End If
         Next
      End If
   Next
   
   'проверим дубликаты имен библиотеки
'   BiblNamesRefresh
'   bolYes = False 'начальное значение
'   For i = 0 To UBound(Bibles) - 1
'      strBiblName = Bibles(i).Name
'      For j = i + 1 To UBound(Bibles)
'         If StrComp(Bibles(j).Name, strBiblName, vbTextCompare) = 0 Then  ' если есть такая
'            Bibles(j).Name = ""  'убираем повторяющееся имя библиотеки
'            bolYes = True 'типа есть пустые строчки и нужно будет почистить библиотеку
'         End If
'      Next
'   Next
'   'если нужно подчищаем библиотеку
'   If bolYes = True Then 'только естли есть пустые строски
'      'переписываем заново библиотеку без пустых имен
'      BiblNamesRefresh
'   End If

Exit Sub
HasError:
   MsgBox Err.Description, vbCritical
   
End Sub

Private Function SearchPath(PathToSearch As String, BiblName As String) As String
   'проверка пути
   'нужно проверить существование пути
   Dim strPath As String
   Dim strValue As String
   Dim intOtvet As Integer
   
   On Error GoTo HasError
   
   strPath = PathToSearch
   'путь должен быть без \ на конце
   If Right(strPath, 1) = "\" Then 'убираем его
      strPath = Mid(strPath, 1, Len(strPath) - 1)
   End If
   '????!!!! 17.11.14 убрал проверку существования пути. при выводе путей в листбокс млжно помечать недоступные пути как-нибудь
   SearchPath = strPath
'   strValue = Dir(strPath, vbDirectory) 'должны получить имя этой папки или "" если ее нет
'   If Len(strValue) <> 0 Then 'если есть такая папка
'      SearchPath = strPath
'   Else 'нет такой папки, то запрос удаления пути
'      Do
'         intOtvet = MsgBox("В библиотеке -" & BiblName & vbCrLf _
'                     & "Не найден путь: " & strPath & vbCrLf _
'                     & "В данном сеансе этот путь учмтываться не будет." _
'                     & "На будущее этот путь можно сохранить, или удалить." _
'                     & "Удалить путь из библиотеки?", vbYesNoCancel, "Не найден путь?")
'         If intOtvet = 7 Then 'нет
'            'заносим путь в массив
'            SearchPath = strPath
'         ElseIf intOtvet = 7 Then 'удалить
'            SearchPath = ""
'         ElseIf intOtvet = 2 Then 'выход
'            FormaExit.Show
'            'если выбрали не выходить из программы, тогда продолжаем
'         End If
'      Loop While intOtvet = 2 'т.е. нажали канцел, а в форме выхода FormaExit нажали отмена
'   End If
   
Exit Function
HasError:
   MsgBox Err.Description, vbCritical
   
End Function

Private Sub BiblNamesRefresh(BiblNum As Integer)
   'перепись Bibles без указпанного номера
   
   Dim intBiblCountBefor As Integer
   Dim BiblesCopy() As Bibl
   Dim i As Integer
   Dim j As Integer
   
   intBiblCountBefor = UBound(Bibles)
   If intBiblCountBefor = 0 Then
      'если была только одна библа
      'по идее, значит и BiblNum должен быть равен 0 ????, может проверить
      bolBiblIs = False
      Erase Bibles 'удаляем библу
   Else
      ReDim BiblesCopy(intBiblCountBefor - 1)
      'копируем во врем массив все библы кроме указанного номера
      For i = 0 To intBiblCountBefor
         If i <> BiblNum Then
            BiblesCopy(j) = Bibles(i)
            j = j + 1
         End If
      Next
      'переписываем основную библу из BiblesCopy
      Bibles = BiblesCopy
   End If
   
'   'т.е. нужно почистить Bibles от пустых имен
'   BiblesCopy = Bibles 'копируе масив
'   Erase Bibles
'   j = 0 'входное значение
'   Erase strArrayTemp
'   For i = 0 To UBound(BiblesCopy)
'      If Len(BiblesCopy(i).Name) <> 0 Then
'         ReDim Preserve strArrayTemp(j)
'         strArrayTemp(j) = BiblesCopy(i).Name
'         j = j + 1
'         'проверяем  пути для этой библиотеки, на повторение и на пустые
'         If BiblesCopy(i).IsPathes = True Then 'если есть пути для этой библиотеки
'            Erase strArrayPathTemp 'очищаем массив
'            p = 0 'входное значение
'            For k = 0 To UBound(BiblesCopy(i).Paths)
'               If Len(BiblesCopy(i).Paths(k)) <> 0 Then
'                  'проверяем остальные пути, если есть такой же то очищанем его
'                  For n = k + 1 To UBound(BiblesCopy(i).Paths)
'                     If BiblesCopy(i).Paths(k) = BiblesCopy(i).Paths(n) Then
'                        BiblesCopy(i).Paths(k) = ""
'                     End If
'                  Next
'                  ReDim Preserve strArrayPathTemp(p)
'                  strArrayPathTemp(p) = BiblesCopy(i).Paths(k)
'                  p = p + 1
'               End If 'Len(BiblesCopy(i).Paths) <> 0
'            Next
'            If p <> 0 Then
'               'копируем массив путей из strArrayPathTemp в BiblesCopy(i)
'               BiblesCopy(i).Paths = strArrayPathTemp '???? не уверен
'               BiblesCopy(i).IsPathes = True
'            End If
'         End If 'BiblesCopy(i).IsPathes = True
'      End If 'Len(BiblesCopy(i).Name) <> 0
'   Next
'
'   'теперь переписываем заново библиотеку без пустых имен
'   If j <> 0 Then 'если в массиве strArrayTemp есть хоть одна библиотка
'      ReDim Bibles(UBound(strArrayTemp))
'      For i = 0 To UBound(strArrayTemp)
'         'находим эту библиотеку в копии BiblesCopy
'         For j = 0 To UBound(BiblesCopy)
'            If BiblesCopy(j).Name = strArrayTemp(i) Then
'               'копируем библиотеку в новую
'               Bibles(i) = BiblesCopy(j) '?????сильно не уверен
''               Bibles(i).Paths = BiblesCopy(j).Paths '?????не уверен
''               Bibles(i).IsPathes = BiblesCopy(j).IsPathes
'               Exit For
'            End If
'         Next
'      Next
'   End If 'j <> 0
   
End Sub

Private Sub WriteBiblesToForm()
   'заполнение формы из массива библиотек Bibles
   'причем пути заполнять не нужно, при выделении имени библиотеки пути пропишутся при ListBoxBiblName_Change
   
   Dim strArrayTemp() As String
   Dim strBiblName As String
   Dim i As Integer
   
   'очищаем листбоксы
   ListBoxBiblName.Clear
   ListBoxPath.Clear
   
   'записываем типовую библиотеку
   ListBoxBiblName.AddItem strStandartBiblName '????выполняется ли процедура change
   
   'нужно проверить сосздан ли массив библиотек, может он пустой (если в ини пусто было)
   If bolBiblIs = False Then 'т.е. библиотеки нет
      Exit Sub
   End If
   
   'имена библиотек в ListBoxBiblName
'   ReDim strArrayTemp(UBound(Bibles), 0)
   For i = 0 To UBound(Bibles)
      ListBoxBiblName.AddItem Bibles(i).Name
   Next
'   ListBoxBiblName.List() = strArrayTemp '?????неуверен
         
   'считываем текущую библиотеку из ини, если нет выделяем первое имя в списке
   strBiblName = FileIni.GetFile(strSectionOther, strKeyCurrentBibl)
   If Len(strBiblName) = 0 Then 'если не установлена текущая библ, то
      'выделяем ервое имя в списке
      ListBoxBiblName.ListIndex = 1
      LabelCurBiblName = ListBoxBiblName.Text
   Else 'есть значение в ини
      'находим эту библиотеку в листбоксе и выделяем ее
      For i = 0 To ListBoxBiblName.ListCount - 1 '???? неуверен, может -1
         If ListBoxBiblName.List(i, 0) = strBiblName Then 'т.е. есть такая библиотека
            ListBoxBiblName.ListIndex = i
            'при изменении индекса листбокса выполняется процедура ListBoxBiblName_Change
         End If
      Next
   End If
   'в текстбокс выводим имя библиотеке
   LabelCurBiblName = strBiblName
   
End Sub

'Public Sub BrowserBibleFiles(BiblName As String)
'   'проверяем все файлы dwg библиотеки
'   'по имени файла, сама библиотека находится в массиве Bibles
'
'   'проверка дубликатов имен файлов
'   'вывод отчета
'
''   Dim i As Integer
''   Dim intFileCount As Integer
''   Dim ProvBibl As Bibl 'проверяемая библиотека
''   Dim saFilesDwg() As String
''   Dim strPath As String
''   Dim strFileNameDWG As String
''
''   'находим библиотеку в массиве
''   For i = 0 To UBound(Bibles)
''      If Bibles(i).Name = BiblName Then
''         ProvBibl.Name = Bibles(i).Name
''         ProvBibl.IsPathes = Bibles(i).IsPathes
''         ProvBibl.Paths = Bibles(i).Paths
''      End If
''   Next
''
''   'проверяем есть ли пути в библиотеке
''   If ProvBibl.IsPathes = False Then
''      MsgBox "Временно. В проверяемой библе нет путей." & ProvBibl.Name
''      Exit Sub
''   End If
''
''   'заполняем массив имен файлов (только dwg), из путей
''   For i = 0 To UBound(ProvBibl.Paths)
''      strPath = ProvBibl.Paths(i)
''      strFileNameDWG = Dir(strPath & ".dwg")
''      Do Until strFileNameDWG = ""
''         'заносим в массив файлов
''         ReDim Preserve saFilesDwg(intFileCount)
''         saFilesDwg(intFileCount) = strFileNameDWG
''         intFileCount = intFileCount + 1
''         'следущий dwg файл в том же пути
''         strFileNameDWG = Dir
''      Loop
''   Next
''
''   '
'
'End Sub

'Private Function MakeArrayFilesDWGFromPath(Path As String) As Variant
'   'составление массива имен файлов dwg в указанном пути
'   'возвращвет массив типа стринг
'   'в случае отсутвия указанного пути - ""
'   'в случае отсутствия файлов dwg - 0
'
'   Dim strPath As String
'   Dim saFilesDwg() As String
'   Dim strFileNameDWG As String
'   Dim i As Integer
'   Dim intFileCount As Integer
'
'   'проверям последний знак в строке пути
'   strPath = Path
'   'путь должен быть без \ на конце
'   If Right(strPath, 1) = "\" Then 'убираем его
'      strPath = Mid(strPath, 1, Len(strPath) - 1)
'   End If
'
'   'проверяем существование пути
'   If Dir(strPath, vbDirectory) = "" Then 'такого пути нет
'      saFilesDwg(0) = ""
'   Else
'      'заполняем массив имен файлов (только dwg), из путей
'      strFileNameDWG = Dir(strPath & "\*.dwg")
'      Do Until strFileNameDWG = ""
'         'заносим в массив файлов
'         ReDim Preserve saFilesDwg(intFileCount)
'         saFilesDwg(intFileCount) = strFileNameDWG
'         intFileCount = intFileCount + 1
'         'следущий dwg файл в том же пути
'         strFileNameDWG = Dir
'      Loop
'
'      If intFileCount = 0 Then
'         ReDim saFilesDwg(0)
'         saFilesDwg(0) = "0"
'      End If
'
'   End If
'
'   MakeArrayFilesDWGFromPath = saFilesDwg
'
'End Function


Private Sub BiblPathRefresh(ByRef Bibla As Bibl, PathNumForDel As Integer)
   
   'перепись пути библы без указпанного номера пути
   
   Dim intPathCountBefor As Integer
   Dim PathCopy() As path
   Dim i As Integer
   Dim j As Integer
   
   intPathCountBefor = UBound(Bibla.Paths)
   If intPathCountBefor = 0 Then
      'если был только один путь
      'по идее, значит и PathNumForDel должен быть равен 0 ????, может проверить
      'и путь должен быть равер "", тоже можно проверить
      Bibla.IsPathes = False
      Erase Bibla.Paths  'удаляем пути
   Else
      ReDim PathCopy(intPathCountBefor - 1)
      'копируем во врем массив все пути кроме указанного номера
      For i = 0 To intPathCountBefor
         If i <> PathNumForDel Then
            PathCopy(j) = Bibla.Paths(i)
            j = j + 1
         End If
      Next
      'переписываем пути
      Bibla.Paths = PathCopy
   End If
   
End Sub

Private Sub AddDublic(sFile As String, Path1 As String, Path2 As String, Optional StandardBibl As Boolean)
   'добавление бубликатов в массив aFilesDubl
   
   Dim i As Integer
   Dim j As Integer
   Dim bolYesFile As Boolean
   Dim bolYesPath1 As Boolean
   Dim bolYesPath2 As Boolean
   Dim intDublic As Integer
   Dim intPathes As Integer
   
   'нужно проверить не было ли уже такого дублирующегося файла и путей
   If bolFilesDublic = False Then
      'значит это первый заход
      ReDim aFilesDubl(0)
      aFilesDubl(0).File = sFile
      ReDim aFilesDubl(0).Paths(1)
      aFilesDubl(0).Paths(0).path = Path1
      aFilesDubl(0).Paths(1).path = Path2
      If StandardBibl = True Then
         aFilesDubl(0).Paths(1).Bibl = strStandartBiblName
      End If
      bolFilesDublic = True
      Exit Sub
   End If

   'перебираем файлы
   For i = 0 To UBound(aFilesDubl)
      If StrComp(aFilesDubl(i).File, sFile, vbTextCompare) = 0 Then
         'проверяем есть ли уже такие пути
         For j = 0 To UBound(aFilesDubl(i).Paths)
            If StrComp(aFilesDubl(i).Paths(j).path, Path1, vbTextCompare) = 0 Then
               bolYesPath1 = True
            ElseIf StrComp(aFilesDubl(i).Paths(j).path, Path2, vbTextCompare) = 0 Then
               bolYesPath2 = True
            End If
         Next
         intPathes = UBound(aFilesDubl(i).Paths) 'кол-во путей у этого дублирующегося файла
         'если путей не было добавляем
         If bolYesPath1 = False And bolYesPath2 = False Then
            'добавляем оба пути
            intPathes = intPathes + 2
            ReDim Preserve aFilesDubl(i).Paths(intPathes)
            aFilesDubl(i).Paths(intPathes - 1).path = Path1
            aFilesDubl(i).Paths(intPathes).path = Path2
         ElseIf bolYesPath1 = False Then
            'добавляем 1 путь
            intPathes = intPathes + 1
            ReDim Preserve aFilesDubl(i).Paths(intPathes)
            aFilesDubl(i).Paths(intPathes).path = Path1
         ElseIf bolYesPath2 = False Then
            'добавляем 2 путь
            intPathes = intPathes + 1
            ReDim Preserve aFilesDubl(i).Paths(intPathes)
            aFilesDubl(i).Paths(intPathes).path = Path2
            If StandardBibl = True Then
               aFilesDubl(0).Paths(1).Bibl = strStandartBiblName
            End If
         End If
         bolYesFile = True
      End If
   Next
   
   'добавляем файл и пути, если не было еще такого файла
   If bolYesFile = False Then
      intDublic = UBound(aFilesDubl) + 1
      ReDim Preserve aFilesDubl(intDublic)
      aFilesDubl(intDublic).File = sFile
      ReDim aFilesDubl(intDublic).Paths(1)
      aFilesDubl(intDublic).Paths(0).path = Path1
      aFilesDubl(intDublic).Paths(1).path = Path2
      If StandardBibl = True Then
         aFilesDubl(0).Paths(1).Bibl = strStandartBiblName
      End If
   End If
   
End Sub

Private Sub DublBiblFileInStandard(sFile As String, Path1 As String)
   'проверка файла в типовой библе
   'заносить в маасив aFilesDubl
   
   Dim i As Integer
   Dim j As Integer
   Dim asFiles() As String
   
   'проверяем есть ли типовая библа и пути в ней
   If StandartBibl.IsPathes = False Then
      'нет путей в типовой библе, выход
      Exit Sub
   End If
   
   'считываем файлы dwg для всех путей типовой библы
   For i = 0 To UBound(StandartBibl.Paths)
      'процедура получения списка файлов в папке, на данный момент времени
      asFiles = SearchFileInFileSystem(StandartBibl.Paths(i).path)
      If asFiles(0) = "" Or asFiles(0) = "0" Then
         'нет папки или нет dwg
         StandartBibl.Paths(i).IsFiles = False
         Erase StandartBibl.Paths(i).FilesDwg
      Else
         StandartBibl.Paths(i).IsFiles = True
         StandartBibl.Paths(i).FilesDwg = asFiles
      End If
   Next
   
   Erase asFiles
   
   'перебираем все пути типовой библы
   For i = 0 To UBound(StandartBibl.Paths)
      If StandartBibl.Paths(i).IsFiles = True Then
         For j = 0 To UBound(StandartBibl.Paths(i).FilesDwg)
            If StrComp(StandartBibl.Paths(i).FilesDwg(j), sFile) = 0 Then
               'процедура добавления дубликата в массив aFilesDubl
               AddDublic sFile, Path1, StandartBibl.Paths(i).path, True
            End If
         Next
      End If
   Next
   
End Sub

Private Function SearchFileInFileSystem(ByVal strPath As String) As Variant
   'возвращает маасив строк имен файлов dwg в папке
   '"" - если нет пути
   '"0" - если нет dwg
   
   Dim objFS As Object
   Dim objFolder As Folder
   Dim objFile As Object
   Dim strValue As String
   Dim strFile As String
   Dim asFiles() As String
   Dim i As Integer
   
   On Error GoTo HasError
   
   'проверим существование пути
   'убираем "\" на конце
   If Right(strPath, 1) = "\" Then
      strPath = Mid(strPath, 1, Len(strPath) - 1)
   End If
   strValue = Dir(strPath, vbDirectory)
   If strValue = "" Then
      ReDim asFiles(0)
      SearchFileInFileSystem = asFiles
      Exit Function
   End If
   
   Set objFS = CreateObject("Scripting.FileSystemObject")
   Set objFolder = objFS.GetFolder(strPath)
   
'   заполняем массив файлов dwg
'   For Each objFile In objFolder.Files
'      If StrComp(Right(objFile.Name, 3), "dwg", vbTextCompare) = 0 Then
'         ReDim Preserve asFiles(i)
'         asFiles(i) = objFile.Name
'         i = i + 1
'      End If
'   Next
   
   'попробую через dir может будет быстрее
   strFile = Dir(strPath & "\*.dwg")
   Do Until Len(strFile) = 0
      ReDim Preserve asFiles(i)
      asFiles(i) = strFile
      i = i + 1
      strFile = Dir
   Loop
   
   If i = 0 Then
      'если нет файлов dwg в папке
      ReDim asFiles(0)
      asFiles(0) = "0"
   End If
   
   SearchFileInFileSystem = asFiles

Exit Function
HasError:
   MsgBox Err.Description, vbCritical
   
End Function

Public Function CheckExistsAllFolderInLib(libPaths() As path) As Boolean
  'проверка доступности всех путей в библиотеке
  'вывод сообщения со списком недоступных путей
  'возвращает true если все пути доступны и false если есть недоступные пути.
  Dim sMsg As String
  Dim i As Integer
  
  CheckExistsAllFolderInLib = True
  
  sMsg = "Недоступные пути в библиотеке " & LabelCurBiblName & ". Проверьте доступность папок:" & vbCrLf & vbCrLf
  For i = 0 To UBound(libPaths)
    If bolFolderExists(libPaths(i).path) = False Then
      sMsg = sMsg & libPaths(i).path & vbCrLf
      CheckExistsAllFolderInLib = False
    End If
  Next
  If CheckExistsAllFolderInLib = False Then
    MsgBox sMsg, vbCritical
  End If
End Function

Public Function RemoveSlashAtEndOfPathFolder(ByRef sPath As String)
  If Right(sPath, 1) = "\" Then 'убираем его
      sPath = Mid(sPath, 1, Len(sPath) - 1)
   End If
End Function

Attribute VB_Name = "FormaAddBibl"
Attribute VB_Base = "0{C7E15F35-E05B-4785-A8B4-E32BAC780FEC}{6E4FD3F6-9947-49C7-A589-79EE9C4E0DC2}"
Attribute VB_GlobalNameSpace = False
Attribute VB_Creatable = False
Attribute VB_PredeclaredId = True
Attribute VB_Exposed = False
Attribute VB_TemplateDerived = False
Attribute VB_Customizable = False
Option Explicit

Private Sub cmbCancel_Click()
   hide
End Sub

Private Sub cmbOK_Click()
   'добавляем библиотеку
   
   Dim strBiblName As String
   Dim i As Integer
   Dim j As Integer
   Dim strArrTemp() As String
   
   On Error GoTo HasError
   
   If TextBoxBiblName = "" Then
      MsgBox "Не введено имя библиотеки"
      Exit Sub
   End If
   
   strBiblName = TextBoxBiblName.Text
   
   'проверим есть ли такое имя уже
   If bolBiblIs = True Then
      For i = 0 To UBound(Bibles)
         If Bibles(i).Name = strBiblName Then
            MsgBox "Такое имя библиотеки уже есть!"
            Exit Sub
         End If
      Next
   End If
   
   'добавляем имя в листбокс библиотек
   FormVyborBibl.ListBoxBiblName.AddItem strBiblName
   'нужно ее выделить, как????
   
   'добавляем библиотеку в массив библиотек
   If bolBiblIs = True Then
      i = UBound(Bibles) + 1
      ReDim Preserve Bibles(i)
      Bibles(i).Name = strBiblName
   Else
      ReDim Bibles(0)
      Bibles(0).Name = strBiblName
      bolBiblIs = True 'создана библиотека
   End If
   
   hide
   
Exit Sub
HasError:
      MsgBox Err.Description, vbCritical
   
End Sub

Private Sub UserForm_Activate()
      
   TextBoxBiblName = "Имя"
      
End Sub

Attribute VB_Name = "FormaBiblRename"
Attribute VB_Base = "0{382EE2C9-9167-4139-9AB1-51DA19457973}{5EC576F6-C3FB-4280-9440-74F785C41B0A}"
Attribute VB_GlobalNameSpace = False
Attribute VB_Creatable = False
Attribute VB_PredeclaredId = True
Attribute VB_Exposed = False
Attribute VB_TemplateDerived = False
Attribute VB_Customizable = False
Option Explicit

Private Sub cmbCancel_Click()
   TextBoxBiblName = ""
   hide
End Sub

Private Sub cmbOK_Click()
   'проверяем введенное значение
   Dim strBiblName As String
   Dim i As Integer
   
   'если в текстбоксе пусто или имя = типовой библиотеке
   If TextBoxBiblName = "" Then
      MsgBox "Не введено имя библиотеки"
      Exit Sub
   End If
   If StrComp(TextBoxBiblName, strStandartBiblName, vbTextCompare) = 0 Then
      MsgBox "Нельзя библиотеку называть -" & strStandartBiblName
      Exit Sub
   End If
   
   strBiblName = TextBoxBiblName.Text
   
   'проверим есть ли такое имя уже
   For i = 0 To UBound(Bibles)
      If Bibles(i).Name = strBiblName Then
         MsgBox "Такое имя библиотеки уже есть!"
         Exit Sub
      End If
   Next
   
   hide 'закрываем форму
   
End Sub

Private Sub UserForm_QueryClose(Cancel As Integer, CloseMode As Integer)
   FormaExit.show
End Sub

Attribute VB_Name = "FormaDublic"
Attribute VB_Base = "0{868A32FE-3656-4EEC-BD12-B0F2124E82E9}{D84DA1BE-2A50-4FFC-B774-598B8B96CAC5}"
Attribute VB_GlobalNameSpace = False
Attribute VB_Creatable = False
Attribute VB_PredeclaredId = True
Attribute VB_Exposed = False
Attribute VB_TemplateDerived = False
Attribute VB_Customizable = False
Option Explicit

Private Sub cmbOK_Click()
   hide
End Sub

Private Sub ListBoxFiles_Change()
   
   Dim i As Integer
   Dim j As Integer
   Dim strFile As String
   
   'записываем в текстбок выделенный файл
   strFile = ListBoxFiles.Text
   TextBoxSelectFilrs = strFile
   
   ListBoxPath.Clear
   
   'выводим список путей для этого файла из массива aFilesDubl
   For i = 0 To UBound(aFilesDubl)
      If aFilesDubl(i).File = strFile Then
         For j = 0 To UBound(aFilesDubl(i).Paths)
            If aFilesDubl(i).Paths(j).Bibl = strStandartBiblName Then
               ListBoxPath.AddItem aFilesDubl(i).Paths(j).path & "(типовая)"
            Else
               ListBoxPath.AddItem aFilesDubl(i).Paths(j).path
            End If
         Next
      End If
   Next
   
End Sub

Private Sub ListBoxFiles_DblClick(ByVal Cancel As MSForms.ReturnBoolean)
   ListBoxFiles_Change
End Sub

Private Sub ListBoxPath_Change()
   TextBoxSelectPath = ListBoxPath.Text
End Sub

Private Sub UserForm_Activate()
   
   Dim i As Integer
   
   ListBoxFiles.Clear
   ListBoxPath.Clear
   
   'считываем имя текущей библы
   LabelBibl = "Библиотека: " & FormVyborBibl.ListBoxBiblName.Text
   
   'заполняем список дублирующихся файлов из
   For i = 0 To UBound(aFilesDubl)
      ListBoxFiles.AddItem aFilesDubl(i).File
   Next
   
   'выделяем первый элемент в списке
   ListBoxFiles.Selected(0) = True
   
End Sub

Attribute VB_Name = "FormaExit"
Attribute VB_Base = "0{8A1C13A7-18B6-441B-A41C-087ED93DB752}{AA66A325-5488-4AA5-989E-02C83A437093}"
Attribute VB_GlobalNameSpace = False
Attribute VB_Creatable = False
Attribute VB_PredeclaredId = True
Attribute VB_Exposed = False
Attribute VB_TemplateDerived = False
Attribute VB_Customizable = False


Private Sub CommandButton1_Click()
''   FormaExit.Hide
''   FormVyborBibl.Hide
'   hide
'   bolExit = True
   Functions.LoadLayersSate
   End
   
End Sub

Private Sub CommandButton2_Click()
   hide
End Sub

Private Sub UserForm_QueryClose(Cancel As Integer, CloseMode As Integer)
   hide
End Sub

Attribute VB_Name = "FormaFreezeBlock"
Attribute VB_Base = "0{8D82B5F1-0350-4724-A37D-96C5D243CBD6}{28462514-CFCE-4006-96B8-BC2BB199CA1E}"
Attribute VB_GlobalNameSpace = False
Attribute VB_Creatable = False
Attribute VB_PredeclaredId = True
Attribute VB_Exposed = False
Attribute VB_TemplateDerived = False
Attribute VB_Customizable = False
Option Explicit


Private Sub cmbExit_Click()
   
   Dim i As Integer
   Dim objLayer As AcadLayer
   
   'если уже была остановлена прога, то конец
   If cmbOK.Visible = False Then
      'возвращаем заморозку
'      For i = 0 To UBound(FreezeBlocks)
'         Set objLayer = ThisDrawing.Layers.Item(FreezeBlocks(i).LayerName)
'         objLayer.Freeze = True
'      Next
      Functions.LoadLayersSate
      End
   End If
   
   'удаляем кнопку продолжить
   cmbOK.Visible = False
   
   dLeft = FormaFreezeBlock.Left
   dTop = FormaFreezeBlock.Top
   
   hide
   FormaFreezeBlock.show vbModeless
   bolFreezeOk = False
   
End Sub

Private Sub cmbOK_Click()
   'возвращаем заморозку слоям и продолжаем прогу
   
   Dim i As Integer
   Dim objLayer As AcadLayer
   Dim intOtvet As Integer
   
   intOtvet = MsgBox("Слои будут разморожены, а блоки будут заменены!" & vbCrLf & _
                     "Продолжить?", vbYesNo)
   If intOtvet = 7 Then 'нет
      Exit Sub
   End If
   
   'возвращаем заморозку
'   For i = 0 To UBound(FreezeBlocks)
'      Set objLayer = ThisDrawing.Layers.Item(FreezeBlocks(i).LayerName)
'      objLayer.Freeze = True
'   Next
   
   bolFreezeOk = True
   
   hide
   
End Sub

Private Sub cmbView_Click()
   'подсвечиваем и зуммируем выбранный блок
   
   Dim objBlock As AcadBlockReference
   Dim strCurLayer As String
   Dim strCurBlock As String
   Dim i As Integer
   Dim j As Integer
   Dim index As Integer
   
   On Error GoTo Ошибка
   
   dLeft = FormaFreezeBlock.Left
   dTop = FormaFreezeBlock.Top
   
   'проверяем выделенн ли элемент списка
   If ListBoxBlocks.Text <> "" Then
      strCurLayer = ListBoxLayers.Text
      strCurBlock = ListBoxBlocks.Text
'      If Right(strBlockName, 7) = "заменен" Then
'         strCurBlock = Mid(strCurBlock, 1, Len(strCurBlock) - 8)
'      End If
      index = ListBoxBlocks.ListIndex
      'находим блок в массиве по индексу
      For i = 0 To UBound(FreezeBlocks)
         If FreezeBlocks(i).LayerName = strCurLayer Then
            Set objBlock = FreezeBlocks(i).colBlocks.Item(index + 1)
            objBlock.Document.Activate
            objBlock.Highlight True
            ZoomCenter objBlock.InsertionPoint, 10000
         End If
      Next
      
   End If

Exit Sub

Ошибка:
   If Err.Number = -2145386420 Then
      MsgBox "Объект был стерт"
      FreezeBlocks(i).colBlocks.Remove index + 1
      ListBoxBlocks.RemoveItem index
   Else
      MsgBox Err.Description
   End If
   
End Sub

Private Sub ListBoxBlocks_Change()
   'записываем выбранный блок
   
   Dim strCurBlock As String
   
   strCurBlock = ListBoxBlocks.Text
   
   TextBoxSelectBlock = strCurBlock
   
End Sub

Private Sub ListBoxBlocks_DblClick(ByVal Cancel As MSForms.ReturnBoolean)
   cmbView_Click
End Sub

Private Sub ListBoxLayers_Change()
   'Для выбранного слоя отобрааем блоки
   
   Dim strCurLayer As String
   Dim i As Integer
   Dim j As Integer
   Dim oBlRef As AcadBlockReference
   
   On Error GoTo Ошибка
   
   strCurLayer = ListBoxLayers.Text
   
   'находим имя слоя в массиве и заполняем список блоков
   For i = 0 To UBound(FreezeBlocks)
      If FreezeBlocks(i).LayerName = strCurLayer Then
         'записывваем имена блоков
         For Each oBlRef In FreezeBlocks(i).colBlocks
'         For j = 0 To FreezeBlocks(i).colBlocks.Count - 1
'            ListBoxBlocks.AddItem FreezeBlocks(i).colBlocks.Item(j + 1).Name, CStr(j)
            ListBoxBlocks.AddItem oBlRef.Name
         Next
      End If
   Next
   
   'записываем текущий выбранный слой
   TextBoxSelectLayer = strCurLayer
   
Exit Sub

Ошибка:
   If Err.Number = -2145386420 Then
      MsgBox "Объект был стерт"
      ListBoxBlocks.AddItem "Удалено"
   Else
      MsgBox Err.Description
   End If
   Resume Next

End Sub

Private Sub UserForm_Activate()
   
   If dLeft <> 0 And dTop <> 0 Then
      FormaOtchet.Left = dLeft
      FormaOtchet.Top = dTop
   End If
   
End Sub

Private Sub UserForm_Initialize()
   'считываем слои из масива FreezeBlocks
   
   Dim i As Integer
   
   If dLeft <> 0 And dTop <> 0 Then
      FormaOtchet.Left = dLeft
      FormaOtchet.Top = dTop
   End If
   
   'выводим список слоев
   For i = 0 To UBound(FreezeBlocks)
      ListBoxLayers.AddItem FreezeBlocks(i).LayerName
   Next
   
End Sub

Attribute VB_Name = "FormaOtchet"
Attribute VB_Base = "0{0A4F0995-B753-4A97-8A0B-1376667D52B1}{136A8D86-6873-4FDA-957E-CB9F4999BDBE}"
Attribute VB_GlobalNameSpace = False
Attribute VB_Creatable = False
Attribute VB_PredeclaredId = True
Attribute VB_Exposed = False
Attribute VB_TemplateDerived = False
Attribute VB_Customizable = False
Option Explicit

'Dim dLeft As Double
'Dim dTop As Double
   
   'тип текущего списка блоков
   Enum ListBoxOtchetType
      Brak = 0
      NotFound = 1
      IzmInsPt = 2
      Nalogenie = 3
   End Enum
   
   Dim colOtchetZBBlocks As New Collection
   
   Dim intListBoxOtchetType As Integer

Private Sub cmbExit_Click()
   hide
   Functions.LoadLayersSate
   End
End Sub

Private Sub cmbIzmInsertPt_Click()
   
   Dim objBlock As AcadBlockReference
   Dim i As Integer
  'могут быть удаленные блоки
  On Error Resume Next
   
   ListBoxBlocks.Clear
   
   'вывести список неопределенных блоков
   For Each objBlock In colIzmInsertPoint
      'надеюсь индексы совпадут ????????????????
      ListBoxBlocks.AddItem objBlock.Name
      If Err Then
        'блок был удален
        colIzmInsertPoint.Remove i
        i = i - 1
        Err.Clear
      End If
      i = i + 1
   Next
   
   'показать кнопку с заменой
   cmbZB.Visible = False
   cmbZBAll.Visible = False
   
   intListBoxOtchetType = ListBoxOtchetType.IzmInsPt
   
   LabelListText = "Список блоков с изменившейся точкой вставки"
   
'   MsgBox "Могу показать только по одному из каждого блока с изменившейся точкой вставки" & vbCrLf & _
'         "А вам нужно исправить все вхождения этого блока на чертеже!"
End Sub

Private Sub cmbNalogenie_Click()
   
   Dim objBlock As AcadBlockReference
   Dim i As Integer
  'могут быть удаленные блоки
  On Error Resume Next
  
   ListBoxBlocks.Clear
   
   'вывести список неопределенных блоков
   For Each objBlock In colBlocksNalogenie
      'надеюсь индексы совпадут ????????????????
      ListBoxBlocks.AddItem objBlock.Name
      If Err Then
        'блок был удален
        colBlocksNalogenie.Remove i
        i = i - 1
        Err.Clear
      End If
      i = i + 1
   Next
   
   'показать кнопку с заменой
   cmbZB.Visible = False
   cmbZBAll.Visible = False
   
   intListBoxOtchetType = ListBoxOtchetType.Nalogenie
   
   LabelListText = "Список блоков на которые возможно накладывается дубликат"

End Sub

Private Sub cmbNeopredel_Click()
   
   Dim objBlock As AcadBlockReference
   Dim i As Integer
  'могут быть удаленные блоки
  On Error Resume Next
   
   ListBoxBlocks.Clear
   
   'вывести список неопределенных блоков
   For Each objBlock In colBlockBrack
      'надеюсь индексы совпадут ????????????????
      ListBoxBlocks.AddItem objBlock.Name
      If Err Then
        'блок был удален
        colBlockBrack.Remove i
        i = i - 1
        Err.Clear
      End If
      i = i + 1
   Next
   
   'показать кнопку с заменой
   cmbZB.Visible = True
   cmbZBAll.Visible = True
   
   intListBoxOtchetType = ListBoxOtchetType.Brak
   
   LabelListText = "Список блоков с атрибутами, но не определенные как жб изделия"
   
End Sub

Private Sub cmbNotFound_Click()
   
   Dim objBlock As AcadBlockReference
   Dim i As Integer
  'могут быть удаленные блоки
  On Error Resume Next
   
   ListBoxBlocks.Clear
   
   'вывести список неопределенных блоков
   For Each objBlock In colBlocksNotFound
      'надеюсь индексы совпадут ????????????????
      ListBoxBlocks.AddItem objBlock.Name
      If Err Then
        'блок был удален
        colBlocksNotFound.Remove i
        i = i - 1
        Err.Clear
      End If
      i = i + 1
   Next
   
   'показать кнопку с заменой
   cmbZB.Visible = False
   cmbZBAll.Visible = False
   
   intListBoxOtchetType = ListBoxOtchetType.NotFound
   
   LabelListText = "Список блоков не найденные в библиотеке"

End Sub

Private Sub cmbView_Click()
   'показать на экране выбранный блок
   
'   Dim i As Integer
'   Dim strFileFullPath As String
'   Dim index As Integer
'   Dim objBlock As AcadBlockReference
'   Dim strBlockName As String
'
'   dLeft = FormaOtchet.Left
'   dTop = FormaOtchet.Top
'
'   index = ListBoxBlocks.ListIndex
'   'если выбран элемент в списке
'   If index = -1 Then
'      Exit Sub
'   End If
'      strBlockName = ListBoxBlocks.Text
'
'      index = index + 1
'      'определяем объект блока, по типу текущего списка
'      Select Case intListBoxOtchetType
'         Case ListBoxOtchetType.Brak
'            'тут может быть произведена замена блока
'            'если это замененный блок
'            If Right(strBlockName, 7) = "заменен" Then
'               'смотрим в коллекцию заменненных блоков
'               Set objBlock = colOtchetZBBlocks.Item(index)
'            Else
'               'находим блок в rjkktrwbb по индексу
'               Set objBlock = colBlockBrack.Item(index)
'            End If
'
'         Case ListBoxOtchetType.IzmInsPt
'            'значит блок из коллекции colIzmInsertPoint
'            Set objBlock = colIzmInsertPoint.Item(index)
'         Case ListBoxOtchetType.NotFound
'            'значит бок из коллекции colBlocksNotFound
'            Set objBlock = colBlocksNotFound.Item(index)
'         Case ListBoxOtchetType.Nalogenie
'            'значит бок из коллекции colBlocksNalogenie
'            Set objBlock = colBlocksNalogenie.Item(index)
'      End Select
'
'
'   'проверяем есть ли блок в чертеже?????, т.е не удалян ли объект ????????как
'   Err.Clear
'   On Error Resume Next
'      'подсвечиваем блок
'      objBlock.Highlight True
'      'зуммируем
'      ZoomCenter objBlock.InsertionPoint, 10000
'      If Err.Number = -2145386420 Then
'         MsgBox "Объект был стерт"
'         Select Case intListBoxOtchetType
'            Case ListBoxOtchetType.Brak
'               colBlockBrack.Remove index
'            Case ListBoxOtchetType.IzmInsPt
'               colIzmInsertPoint.Remove index
'            Case ListBoxOtchetType.NotFound
'               colBlocksNotFound.Remove index
'            Case ListBoxOtchetType.Nalogenie
'               colBlocksNalogenie.Remove index
'         End Select
'         ListBoxBlocks.RemoveItem index - 1
'      ElseIf Err.Number <> 0 Then
'         MsgBox Err.Description, vbCritical
'      End If
'
Dim objBlock As AcadBlockReference
   Dim index As Integer
   
   On Error GoTo HasError
   
   index = ListBoxBlocks.ListIndex
   If index = -1 Then
      Exit Sub
   End If
   
   index = index + 1
   Select Case intListBoxOtchetType
      Case ListBoxOtchetType.Brak
         Set objBlock = colBlockBrack.Item(index)
      Case ListBoxOtchetType.IzmInsPt
         Set objBlock = colIzmInsertPoint.Item(index)
      Case ListBoxOtchetType.Nalogenie
         Set objBlock = colBlocksNalogenie.Item(index)
      Case ListBoxOtchetType.NotFound
         Set objBlock = colBlocksNotFound.Item(index)
   End Select
   
   objBlock.Document.Activate
   objBlock.Highlight True
   ZoomCenter objBlock.InsertionPoint, 10000
   
Exit Sub
HasError:
   Select Case Err.Number
      Case -2145386420
         MsgBox "Блок был удален", vbCritical
         Select Case intListBoxOtchetType
            Case ListBoxType.Brack
               colBlockBrack.Remove (index)
            Case ListBoxOtchetType.IzmInsPt
               colIzmInsertPoint.Remove (index)
            Case ListBoxOtchetType.Nalogenie
               colBlocksNalogenie.Remove (index)
            Case ListBoxOtchetType.NotFound
               colBlocksNotFound.Remove (index)
         End Select
         ListBoxBlocks.RemoveItem index - 1
   End Select
      
End Sub

Private Sub cmbZB_Click()
   'сделать процедуру замены для выбранного блока
   'возможно только для блока из коллекции забракованных блоков colBlockBrack
   
   Dim strFileFullPath As String
   Dim index As Integer
   Dim objBlock As AcadBlockReference
   Dim objBlockZB As AcadBlockReference
   Dim strBlockName As String
   
On Error GoTo Ошибка
   
   If intListBoxOtchetType <> ListBoxOtchetType.Brak Then
      'только для блока из коллекции colBlockBrack
      Exit Sub
   End If
   
      strBlockName = ListBoxBlocks.Text
      index = ListBoxBlocks.ListIndex
      If index = -1 Then
         Exit Sub
      End If
      index = index + 1
      'находим блок в массиве по индексу
      'нужна проверка, если блок был удален
      Set objBlock = colBlockBrack.Item(index)
      'операция зб
      objBlock.Highlight True 'просто для проверки что блок не удален
      Set objBlockZB = PrinudZamenaBlocka(objBlock)
      If objBlockZB Is Nothing = True Then
         Exit Sub
      End If
      
      'удаляем блок из коллекции неопределеннных блоков
      colBlockBrack.Remove index
      
      'добавляем замененнный блок в колекцию замененных блоков
      colOtchetZBBlocks.add objBlockZB
   
      'прибавляем кол-во замененных блоков
      LabelKolZB = "Количество замененных блоков жб изделий: " & intKolZB
      'удаляем запись из листвиевера
      ListBoxBlocks.RemoveItem index - 1
      
      MsgBox "Блок заменен. Проверте положение атрибута!"

Exit Sub
   
Ошибка:
   If Err.Number = -2145386420 Then
      MsgBox "Объект был стерт"
      colBlockBrack.Remove index
      ListBoxBlocks.RemoveItem index - 1
      Exit Sub
   Else
      MsgBox Err.Description
   End If

End Sub

Private Sub cmbZBAll_Click()
   'замена всех блоков из списка неопределенных блоков
   
   Dim strFileFullPath As String
   Dim index As Integer
   Dim objBlock As AcadBlockReference
   Dim objBlockZB As AcadBlockReference
   Dim strBlockName As String
   
   On Error GoTo Ошибка
   
   If colBlockBrack.Count = 0 Then
      MsgBox "Нет блоков для замены"
      Exit Sub
   End If
   
   If intListBoxOtchetType <> ListBoxOtchetType.Brak Then
      'только для блока из коллекции colBlockBrack
      MsgBox "Выберете неопределенные блоки (кнопка)"
      Exit Sub
   End If
   
   If MsgBox("Сделать Замену всех блоков из списка неопределенных блоков", vbQuestion + vbYesNo) = vbNo Then Exit Sub
   
   For index = 0 To ListBoxBlocks.ListCount - 1
      'находим блок в массиве по индексу
      Set objBlock = colBlockBrack.Item(index + 1)
      'операция зб
      objBlock.Highlight True 'просто для проверки что блок не удален
      Set objBlockZB = PrinudZamenaBlocka(objBlock)
      If objBlockZB Is Nothing = True Then
         Exit Sub
      End If
      
      'добавляем замененнный блок в колекцию замененных блоков
      colOtchetZBBlocks.add objBlockZB
      
      intKolZB = intKolZB + 1
      
   Next
   
   'очищаем коллекцию
   Set colBlockBrack = New Collection
   
   'прибавляем кол-во замененных блоков
   LabelKolZB = "Количество замененных блоков жб изделий: " & intKolZB
   
   'выводим список замененных блоков
   ListBoxBlocks.Clear
'   'отсортировать блоки в коллекции
'   Call Functions.SortyrBlInCol(colOtchetZBBlocks)
   For Each objBlock In colOtchetZBBlocks
      ListBoxBlocks.AddItem objBlock.Name & " заменен"
   Next
   
   MsgBox "Блоки заменены. Проверте их положение, возможно измененилась точка вставки!"

Exit Sub
   
Ошибка:
   If Err.Number = -2145386420 Then
      MsgBox "Объект был стерт"
      colBlockBrack.Remove index
      ListBoxBlocks.RemoveItem index - 1
      Resume
   Else
      MsgBox Err.Description
   End If
   
End Sub

Private Sub ListBoxBlocks_Change()
   'показываем кнопку "показать"
   cmbView.Enabled = True
   
End Sub

Private Sub ListBoxBlocks_DblClick(ByVal Cancel As MSForms.ReturnBoolean)
   cmbView_Click
End Sub

Private Sub UserForm_Activate()

'   If dLeft <> 0 And dTop <> 0 Then
'      FormaOtchet.Left = dLeft
'      FormaOtchet.Top = dTop
'   End If
   
End Sub

Public Function PrinudZamenaBlocka(ByRef objBlock As AcadBlockReference) As AcadBlockReference
   'замена блока на чертеже библиотечным
   'записываем положение атрибута
   'принудительная замена без проверки атрибутов
   
   Dim objInsertBlock As AcadBlockReference
   Dim objAtr As AcadAttributeReference
   Dim objAtrInviz As AcadAttributeReference
   Dim objLayer As AcadLayer
   Dim varAtrPt As Variant
   Dim varAtr As Variant
   Dim dAtrRot As Double
   Dim strLayer As String
   Dim strFileFullPath As String
   Dim intOtvet As Integer
   Dim i As Integer
   Dim bolYes As Boolean
   Dim dXScale As Double
   Dim dYScale As Double
   
   On Error GoTo HasError
   
   'определяем положение атрибута, марки
      For Each varAtr In objBlock.GetAttributes
          Set objAtr = varAtr
         If objAtr.Layer = "Att~Marka" Then
            'только если он видимый
            If objAtr.Invisible = False Then
               varAtrPt = objAtr.InsertionPoint
               dAtrRot = objAtr.Rotation
               bolYes = True
            End If
          End If
          If objAtr.Invisible = False Then
            Set objAtrInviz = objAtr
         End If
      Next
      'если не найден атрибут марки, то
      If bolYes = False Then
            varAtrPt = objAtrInviz.InsertionPoint
            dAtrRot = objAtrInviz.Rotation
      End If
      'проверяем слой блока, чтобы его удалить, может и не нужно?????проверить
      Set objLayer = ThisDrawing.Layers.Item(objBlock.Layer)
      objLayer.Lock = False
      'проверка замороженности и отключенности слоя актуальна для выбора всех блоко чертежа, кажется ?????
      If Not objLayer Is ThisDrawing.ActiveLayer Then
         objLayer.Freeze = False
      End If
      objLayer.LayerOn = True
      
      'проверяем зеркальность этого блока
'      If Sgn(objBlock.XScaleFactor) = -1 Or Sgn(objBlock.YScaleFactor) = -1 Then 'если отрицательное число, значит отзеркален
         dXScale = objBlock.XScaleFactor
         dYScale = objBlock.YScaleFactor
'      End If 'если отрицательное число
      
      'находим путь к блоку в библиотеке
      strFileFullPath = SearchFileInBibl(objBlock.Name & ".dwg", objBlock)
      If strFileFullPath = "" Then 'значит файл не найден ни в основной ни в типовой библиотеках
         objBlock.Highlight True
         ZoomCenter objBlock.InsertionPoint, 10000
         MsgBox "Блок " & objBlock.Name & " - не найден в библиотеке!"
         'выход
         Set PrinudZamenaBlocka = Nothing
         Exit Function
      End If
      Set objInsertBlock = ThisDrawing.ModelSpace.InsertBlock(objBlock.InsertionPoint, strFileFullPath, objBlock.XScaleFactor, objBlock.YScaleFactor, objBlock.ZScaleFactor, objBlock.Rotation)
      'подсчитываем кол-во замененных блоков
      intKolZB = intKolZB + 1
      'переводим в слой блоков изделий
      objInsertBlock.Layer = strLayerBlockIzd
      
      objInsertBlock.XScaleFactor = dXScale
      objInsertBlock.YScaleFactor = dYScale
      
      'устанавливаем положение атрибута
      For Each varAtr In objInsertBlock.GetAttributes
         Set objAtr = varAtr
         If objAtr.Layer = "Att~Marka" Then
            objAtr.Rotation = dAtrRot
            objAtr.Move objAtr.InsertionPoint, varAtrPt
            Exit For
         End If
      Next
      objInsertBlock.Highlight True
      objBlock.Delete 'удаляем старый блок
      
      Set PrinudZamenaBlocka = objInsertBlock

Exit Function
HasError:
   MsgBox Err.Description, vbCritical
   
End Function

Private Sub UserForm_Initialize()
   'проверяем коллекции и показываем соответствующие кнопки
   
   Dim bolOk As Boolean
   
   On Error GoTo HasError
   
   'неопределенные блоки, т.е. блоки с атрибутами но без материала=Железобетон
   If colBlockBrack.Count <> 0 Then
      'показываем кнопку с неопределенными блоками
      cmbNeopredel.Visible = True
      bolOk = True
      'отсортировать блоки в коллекции
      Call Functions.SortyrBlInCol(colBlockBrack)
   End If
   
   'блоки не найденные в библиотеке
   If colBlocksNotFound.Count <> 0 Then
      'показываем кнопку с не найденными блоками
      cmbNotFound.Visible = True
      bolOk = True
      'отсортировать блоки в коллекции
      Call Functions.SortyrBlInCol(colBlocksNotFound)
   End If
   
   'блоки с изменившейся точкой вставки
   If colIzmInsertPoint.Count <> 0 Then
      'показываем кнопку с блоками с изменившейся точкой вставки
      cmbIzmInsertPt.Visible = True
      bolOk = True
      
      'ищем все эти блоки в начальном наборе для ЗБ
      Dim i As Integer
      Dim objBlRef As AcadBlockReference
      Dim objBlRefSel As AcadBlockReference
      Dim aoBlRef() As AcadBlockReference
      
      i = colIzmInsertPoint.Count - 1
      ReDim aoBlRef(0 To i)
      i = 0
      For Each objBlRef In colIzmInsertPoint
         Set aoBlRef(i) = objBlRef
         i = i + 1
      Next
      Set colIzmInsertPoint = Nothing
      For i = 0 To UBound(aoBlRef)
         For Each objBlRefSel In colZB
            If aoBlRef(i).Name = objBlRefSel.Name Then
               colIzmInsertPoint.add objBlRefSel
            End If
         Next
      Next
      'отсортировать блоки в коллекции
      Call Functions.SortyrBlInCol(colIzmInsertPoint)
   End If
   
   'блоки возможного наложения
   If colBlocksNalogenie.Count <> 0 Then
      'показываем кнопку
      cmbNalogenie.Visible = True
      bolOk = True
      'отсортировать блоки в коллекции
      Call Functions.SortyrBlInCol(colBlocksNalogenie)
   End If
   
   'если нет ни одного списка, то скрываеми его
   If bolOk = False Then
      LabelListText.Visible = False
      ListBoxBlocks.Visible = False
      'уменьшаем размеры формы
      FormaOtchet.Height = 115
      cmbExit.Top = 67.5
   End If
   
Exit Sub
HasError:
   MsgBox Err.Description, vbCritical
   
End Sub

Private Sub UserForm_QueryClose(Cancel As Integer, CloseMode As Integer)
   hide
   Functions.LoadLayersSate
   End
End Sub

Attribute VB_Name = "FormaProverky"
Attribute VB_Base = "0{CE70B1A4-D426-49B8-BD1F-A6CF02C4FA18}{CAC8AE8B-21FD-4EED-952A-84B9CEF26B50}"
Attribute VB_GlobalNameSpace = False
Attribute VB_Creatable = False
Attribute VB_PredeclaredId = True
Attribute VB_Exposed = False
Attribute VB_TemplateDerived = False
Attribute VB_Customizable = False
Option Explicit
   
   'тип текущего списка блоков
   Enum ListBoxType
      ErrName = 0
      Zerkal = 1
      Nalogenie = 2
      Brack = 3
   End Enum
   
   Dim intListBoxType As Integer

Private Sub cmbErrName_Click()
   Dim objBlock As AcadBlockReference
   Dim i As Integer
  'могут быть удаленные блоки
  On Error Resume Next
  
   ListBoxBlocks.Clear
   
   'вывести список неопределенных блоков
   For Each objBlock In colBlocksErrName
      'надеюсь индексы совпадут ????????????????
      ListBoxBlocks.AddItem objBlock.Name
      If Err Then
        'блок был удален
        colBlocksErrName.Remove i
        i = i - 1
        Err.Clear
      End If
      i = i + 1
   Next
   
   LabelPrimech = "Пояснение: В которых атрибут марки не равен имени самого блока!"
   
   intListBoxType = ListBoxType.ErrName
   
End Sub

Private Sub cmbExit_Click()
   Functions.LoadLayersSate
   End
End Sub

Private Sub cmbOK_Click()
   'все по новой
   
   Dim bolYes As Boolean
   Dim bolMaterial As Boolean
   Dim objBlRef As AcadBlockReference
   Dim varAtr As Variant
   
   bolProverka = True
   
   If MsgBox("Продолжить замену блоков?", vbQuestion + vbYesNo) = vbNo Then
      Exit Sub
   End If

   If bolYes = True Then
      cmbView.Enabled = True
   End If
   
   'если были неопределенные блоки делаем их определенными (атрибут Материал=Железобетон)
   If colBlockBrack.Count <> 0 Then
      For Each objBlRef In colBlockBrack
         For Each varAtr In objBlRef.GetAttributes
            If LCase(varAtr.Layer) = "att~material" Then
               varAtr.TextString = "Железобетон"
               bolMaterial = True
               Exit For
            End If
         Next
         'если нет атрибута на слое "Att~Material", может есть атрибут = "железобетон"
         If bolMaterial = False Then
            For Each varAtr In objBlRef.GetAttributes
               If LCase(varAtr.TextString) = "железобетон" Then
                  'переводим атрибут на слой материала
                  varAtr.Layer = "Att~Material"
                  Exit For
               End If
            Next
         End If
      Next
   End If
   
   hide
End Sub

Private Sub cmbNalog_Click()
   
   Dim objBlock As AcadBlockReference
   Dim i As Integer
  'могут быть удаленные блоки
  On Error Resume Next
  
   ListBoxBlocks.Clear
   
   'вывести список неопределенных блоков
   For Each objBlock In colBlocksNalogenie
      'надеюсь индексы совпадут ????????????????
      ListBoxBlocks.AddItem objBlock.Name
      If Err Then
        'блок был удален
        colBlocksNalogenie.Remove i
        i = i - 1
        Err.Clear
      End If
      i = i + 1
   Next
   
   intListBoxType = ListBoxType.Nalogenie
   
   LabelPrimech = "Пояснение: возможно дублирующиеся блоки"
   
End Sub

Private Sub cmbNeopredel_Click()
   Dim objBlock As AcadBlockReference
   
   ListBoxBlocks.Clear
   
   'вывести список неопределенных блоков
   For Each objBlock In colBlockBrack
      'надеюсь индексы совпадут ????????????????
      ListBoxBlocks.AddItem objBlock.Name
   Next
End Sub

Private Sub cmbNeopr_Click()
   Dim objBlock As AcadBlockReference
   Dim i As Integer
  'могут быть удаленные блоки
  On Error Resume Next
  
   ListBoxBlocks.Clear
   
   'вывести список неопределенных блоков
   For Each objBlock In colBlockBrack
      'надеюсь индексы совпадут ????????????????
      ListBoxBlocks.AddItem objBlock.Name
      If Err Then
        'блок был удален
        colBlockBrack.Remove i
        i = i - 1
        Err.Clear
      End If
      i = i + 1
   Next
   
   LabelPrimech = "Пояснение: В которых атрибут материала (на слое Att~Material) <> Железобетон"
   
   intListBoxType = ListBoxType.Brack
   
End Sub

Private Sub cmbStop_Click()
   bolProverka = False
   cmbOK.Visible = False
   cmbStop.Visible = False
   cmbExit.Visible = True
   hide
   FormaProverky.show vbModeless
End Sub

Private Sub cmbView_Click()
   
   Dim objBlock As AcadBlockReference
   Dim index As Integer
   
   On Error GoTo HasError
   
   index = ListBoxBlocks.ListIndex
   If index = -1 Then
      Exit Sub
   End If
   
   index = index + 1
   Select Case intListBoxType
      Case ListBoxType.ErrName
         Set objBlock = colBlocksErrName.Item(index)
      Case ListBoxType.Nalogenie
         Set objBlock = colBlocksNalogenie.Item(index)
      Case ListBoxType.Zerkal
         Set objBlock = colBlocksZerkal.Item(index)
      Case ListBoxType.Brack
         Set objBlock = colBlockBrack.Item(index)
   End Select
   
   objBlock.Document.Activate
   
   objBlock.Highlight True
   ZoomCenter objBlock.InsertionPoint, 10000

Exit Sub
HasError:
   Select Case Err.Number
      Case -2145386420
         MsgBox "Блок был удален", vbCritical
         Select Case intListBoxType
            Case ListBoxType.ErrName
               colBlocksErrName.Remove (index)
            Case ListBoxType.Nalogenie
               colBlocksNalogenie.Remove (index)
            Case ListBoxType.Zerkal
               colBlocksZerkal.Remove (index)
            Case ListBoxType.Brack
               colBlockBrack.Remove (index)
         End Select
         ListBoxBlocks.RemoveItem index - 1
      Case Else
         MsgBox Err.Description, vbCritical
   End Select

End Sub

Private Sub cmbZerkal_Click()
   Dim objBlock As AcadBlockReference
   Dim i As Integer
  'могут быть удаленные блоки
  On Error Resume Next
  
   ListBoxBlocks.Clear
   
   'вывести список неопределенных блоков
   For Each objBlock In colBlocksZerkal
      'надеюсь индексы совпадут ????????????????
      ListBoxBlocks.AddItem objBlock.Name
      If Err Then
        'блок был удален
        colBlocksZerkal.Remove i
        i = i - 1
        Err.Clear
      End If
      i = i + 1
   Next
   
   LabelPrimech = "Пояснение: Блок отзеркален в одном из направлений"
   
   intListBoxType = ListBoxType.Zerkal
   
End Sub

Private Sub UserForm_Activate()
   'проверяем коллекции блоков с ошибками и отображаем кнопки
   
   Dim bolYes As Boolean
   
   If colBlocksNalogenie.Count <> 0 Then
      'показываем кнопку
      cmbNalog.Visible = True
      bolYes = True
      'отсортировать блоки в коллекции
      Call Functions.SortyrBlInCol(colBlocksNalogenie)
   End If
   If colBlocksErrName.Count <> 0 Then
      'показываем кнопку
      cmbErrName.Visible = True
      bolYes = True
      'отсортировать блоки в коллекции
      Call Functions.SortyrBlInCol(colBlocksErrName)
   End If
   If colBlocksZerkal.Count <> 0 Then
      'показываем кнопку
      cmbZerkal.Visible = True
      bolYes = True
      'отсортировать блоки в коллекции
      Call Functions.SortyrBlInCol(colBlocksZerkal)
   End If
   If colBlockBrack.Count <> 0 Then
      'показываем кнопку
      cmbNeopr.Visible = True
      bolYes = True
      'отсортировать блоки в коллекции
      Call Functions.SortyrBlInCol(colBlockBrack)
   End If
   
   If bolYes = True Then
      cmbView.Enabled = True
   End If
   
End Sub

Attribute VB_Name = "FormaSelectionSet"
Attribute VB_Base = "0{5675A405-7FFA-445C-9F28-A253F3F7832D}{30D2467A-1C47-4265-AF14-3762C86BD200}"
Attribute VB_GlobalNameSpace = False
Attribute VB_Creatable = False
Attribute VB_PredeclaredId = True
Attribute VB_Exposed = False
Attribute VB_TemplateDerived = False
Attribute VB_Customizable = False


Option Explicit

Private Sub CommandButtonAll_Click()
   bolAllorOnscreen = True 'выбор всех элементов чертежа
   hide
End Sub

Private Sub CommandButtonOnscreen_Click()
   bolAllorOnscreen = False 'выбор рамкой
   hide
End Sub

Private Sub UserForm_QueryClose(Cancel As Integer, CloseMode As Integer)
   FormaExit.show
End Sub

Attribute VB_Name = "FormaSupportPathFind"
Attribute VB_Base = "0{7D91E5F5-DC9D-4973-8022-790C347FB21A}{5FA4666E-57AC-4D02-9AD3-C54890AC4CD0}"
Attribute VB_GlobalNameSpace = False
Attribute VB_Creatable = False
Attribute VB_PredeclaredId = True
Attribute VB_Exposed = False
Attribute VB_TemplateDerived = False
Attribute VB_Customizable = False
Option Explicit


Private Sub cmbExit_Click()
   FormaExit.show
End Sub

Private Sub cmbOK_Click()
   'проверяем выбран ли путь
   Dim strValue As String
   If ListBoxFindPath.Text = "" Then
      MsgBox "Выберете путь"
   Else
      hide
   End If
End Sub

Private Sub UserForm_Click()

End Sub

Attribute VB_Name = "Functions"
Option Explicit

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.add(strSelName)
   
End Function


Public Function GetLayer(strLayerName As String) As AcadLayer
   'возвращает объект слоя, с заданным именем
   'если слоя с таким именем не было, он создается
   
   On Error GoTo HasError
   Set GetLayer = ThisDrawing.Layers.Item(strLayerName)

Exit Function

HasError:
   Set GetLayer = ThisDrawing.Layers.add(strLayerName)
   
End Function


Public Function SortyrBlInCol(colBl As Collection)
   'сортировка блоков в коллекции, по имени
   
   Dim objBlRefTemp As AcadBlockReference
   Dim i As Integer
   Dim j As Integer
   Dim intCount As Integer
   
   intCount = colBl.Count - 1
   
   For i = 1 To intCount
      For j = 1 To intCount - i
         If StrComp(colBl.Item(j).Name, colBl.Item(j + 1).Name, vbTextCompare) = 1 Then
            Set objBlRefTemp = colBl.Item(j)
            colBl.Remove j
            colBl.add objBlRefTemp, , , j
         End If
      Next
   Next
   
End Function

Public Function SaveLayersState()
  'Сохранение состояния слоев
  
  Dim oAcLayerManager As AcadLayerStateManager
  
  On Error Resume Next
  
  Set oAcLayerManager = ThisDrawing.Application.GetInterfaceObject("AutoCAD.AcadLayerStateManager.17")
  oAcLayerManager.SetDatabase ThisDrawing.Database
  
  oAcLayerManager.Delete "ZB"
  oAcLayerManager.Save "ZB", acLsFrozen + acLsOn + acLsLocked
  
End Function

Public Function LoadLayersSate()
  'Восстановление состояния слоев
  
  Dim oAcLayerManager As AcadLayerStateManager
  
  On Error Resume Next
  
  Set oAcLayerManager = ThisDrawing.Application.GetInterfaceObject("AutoCAD.AcadLayerStateManager.17")
  oAcLayerManager.SetDatabase ThisDrawing.Database
  
  oAcLayerManager.Restore "ZB"
  oAcLayerManager.Delete "ZB"
  
End Function

Public Function bolFolderExists(path As String) As Boolean
  'проверка доступности пути
  On Error GoTo HasError
  If Dir(path, vbDirectory) <> "" Then
    bolFolderExists = True
  End If
Exit Function
HasError:
  bolFolderExists = False
End Function

Attribute VB_Name = "Main"
Option Explicit
'Замена блоков чертежа (переопределение) на блоки из библиотеки

'Dim adDoInserta() As Double
'Dim adPosleInserta() As Double
'Dim intCount As Integer

   Public bolExit As Boolean

   Public Type path
      path As String
      FilesDwg() As String
      IsFiles As Boolean
   End Type
   
   Public Type Bibl
      Name As String
      Paths() As path
      IsPathes As Boolean 'для проверки есть ли пути
   End Type
   
   Type FreezeBlock
      LayerName As String
      colBlocks As Collection
      IsBlocks As Boolean
   End Type
   
   Type DublicPath
      path As String
      Bibl As String
   End Type
   
   Type DublicFiles
      File As String
      Paths() As DublicPath
   End Type
   
Public bolAllorOnscreen As Boolean
Public objSelSet As AcadSelectionSet
   
   'переменные для работы с ини файлом библиотек
'   Public strBiblNames() As String 'массив для имен библиотек из ини файла
'   Public strPaths() As String 'массив 2 порядка для путей по номеру каждой библиотеки
   Public FileIni As New ClassINI
   Public Const strFileIniName As String = "ZB.ini"
   Public strMacroPath As String 'путь к макросу, без "\" на конце
   Public Const strSectionBibl As String = "Имена библиотек блоков"
   Public Const strKeyCurrentBibl As String = "Текущая библиотека"
   Public Const strKeyForPathDefault As String = "Путь для поиска"
   Public Const strSectionOther As String = "Прочее"
   Public Const strSectionStandartBibl As String = "Типовая"
   Public bolBiblIs As Boolean 'для поверки был ли создан массив Bibles
'   Public bolStandarBiblIs As Boolean
   Public Const strStandartBiblName As String = "Типовая"
   
   Public Bibles() As Bibl 'массив библиотек
   Public CurBibl As Bibl 'текущая библиотека для операции замены боков
   Public StandartBibl As Bibl   'библиотека типовых изделий
   
   Public intKolZB As Integer 'количество замененных блоков жб изделий
   
   Public FreezeBlocks() As FreezeBlock  'массив замороженных слоев и блоков на них
   Public bolFreezeOk As Boolean
   
   Dim Finish As Double
   Dim Start As Double
   Dim TotalTimeMin As Double
   
   'для сохранения положения окна замороженных слоев
   Public dLeft As Double
   Public dTop As Double
   
   Public Const strLayerBlockIzd As String = "Блоки изделий" 'слой для блоков изделий (у которых атрибут материала=железобетон)
   Public pbInsertBlocksToLayerGBI As Boolean 'флаг вставки блоков на слой "Блоки изделий", да/нет
   
   'Public blockArrayBrack() As AcadBlockReference  'перечень забракованных блоков (т.е. не блоков жб. изделий)
   Public colBlockBrack As New Collection  'перечень забракованных блоков (т.е. не блоков жб. изделий)
   Public bolBrack As Boolean
   Public colIzmInsertPoint As New Collection  'коллекция для блоков с изменившейся точкой вставки
'   Dim intCountIzmPt As Integer
   Public colBlocksNotFound As New Collection  'коллекция для блоков не найденных в библиотеке
'   Dim intCountNotFound As Integer
   Public colBlocksNalogenie As New Collection
'   Dim intCountNalogenie As Integer
   
   Public colBlocksZerkal As New Collection  'зеркальные блоки при проверке
   Public colBlocksErrName As New Collection  'блоки у которых значение атрибута марки не равно имени блока
   
   Public aFilesDubl() As DublicFiles
   
   Public colZB As New Collection
   
   Public bolProverka As Boolean
   
Public Sub Main()

   On Error GoTo HasError

   Set colZB = Nothing
   Set objSelSet = Nothing
   bolAllorOnscreen = False
   strMacroPath = ""
   bolBiblIs = False
   Erase Bibles
   Erase CurBibl.Paths
   CurBibl.IsPathes = False
   CurBibl.Name = ""
   Erase StandartBibl.Paths
   StandartBibl.IsPathes = False
   StandartBibl.Name = ""
   intKolZB = 0
   Erase FreezeBlocks
   bolFreezeOk = False
   dLeft = 0
   dTop = 0
   Set colBlockBrack = Nothing
   bolBrack = False
   Set colIzmInsertPoint = Nothing
   Set colBlocksNotFound = Nothing
   Set colBlocksNalogenie = Nothing
   Set colBlocksZerkal = Nothing
   Set colBlocksErrName = Nothing
   Erase aFilesDubl
   bolProverka = False


   Dim objAcadObj As AcadObject
   Dim objBlockRef As AcadBlockReference
   Dim objaBlockRef(0) As AcadBlockReference
   Dim objInsertBlock As AcadBlockReference
   Dim selSetBlockNames As AcadSelectionSet
   Dim objAttRef As AcadAttributeReference
   Dim objSelSetTemp As AcadSelectionSet
   Dim bolDaNet As Boolean
   Dim strBlockName As String
   Dim strPathBibl As String
   Dim strPathBlock As String
   Dim strTextString As String
   Dim strValue As String
   Dim strLayer As String
   Dim InsertPoint(0 To 2) As Double
   Dim varItem As Variant
'   Dim colBlockDrawing As New Collection
   Dim lCounter As Long
   Dim intOtvet As Integer
   Dim intValue As Integer
   Dim objItemAtr As AcadAttributeReference
   Dim varValue As Variant
   Dim varAtrOrig As Variant
   Dim varAtrCur As Variant
   Dim varItemAtr As Variant
   Dim strInsertFile As String
   Dim strAtr(0 To 4) As String
   Dim i As Integer
   Dim intLen As Integer
   Dim intFilterType(1) As Integer
   Dim varFilterDate(1) As Variant
   Dim strCurBiblName As String
   Dim varAtr As Variant
   
   'старт таймера
   Start = Timer
   
   intKolZB = 0
   bolAllorOnscreen = False
   bolBiblIs = False
   bolFreezeOk = False
   bolBrack = False
   Set colIzmInsertPoint = Nothing
   Set colBlocksNotFound = Nothing
   Set colBlockBrack = Nothing
   Set colBlocksNalogenie = Nothing
   Set FileIni = Nothing
   Erase Bibles
   Erase FreezeBlocks
   bolExit = False
   
'******* Проверка наличия блоков на чертеже *******************
   
   For Each objAcadObj In ThisDrawing.ModelSpace 'перебор всех объектов чертежа
      If objAcadObj.ObjectName = "AcDbBlockReference" Then
         Set objBlockRef = objAcadObj
         If objBlockRef.HasAttributes = True Then
            For Each varAtr In objBlockRef.GetAttributes
               Set objAttRef = varAtr
               If objAttRef.Layer = "Att~Material" Then
'                  If StrComp(objAttRef.TextString, "железобетон", vbTextCompare) = 0 Then
                     'ну типа есть блоки изделий , значит можно продолжать
                     bolDaNet = True
'                     Set objBlockRef = Nothing
                     Exit For
'                  End If
               End If
            Next
         End If
      End If
   Next 'objAcadObj
   
   If bolDaNet = False Then
      MsgBox "Блоки изделий на этом чертеже не найдены!? Выход."
      End
   End If
   
   'Сохранение состояния слоев
   Functions.SaveLayersState
   
   'проверка наличия блоков изделия на замороженных слоях
   If ProvBlockIzdOnFreezeLayers = False Then
      'если нажали выйти из проги
      GoTo Конец
   End If

'******* Конец Проверка наличия блоков на чертеже *******************

'----- Проверка всех блоков, зеркальнось, наложение и т.д. -----------
   
   bolProverka = False 'входное значение
   'все проверки, и занесение ошибочных блоков в коллекции
   AllProverks
   'если найдены ошибки отображаем форму
   If bolProverka = True Or colBlockBrack.Count <> 0 Then
      'форма для исправлений
      FormaProverky.show
      If bolProverka = False Then
         GoTo Конец
      End If
   Else
'      intOtvet = MsgBox("Проверка прошла успешно. Выполнить замену блоков?", vbYesNo)
'      If intOtvet = 7 Then 'нет
'         GoTo Конец
'      End If
   End If

'----- Выбор библиотеки -------

   Dim j As Integer
   'форма выбора библиотеки
   FormVyborBibl.show
   If bolExit = True Then
      GoTo Конец
   End If
   
   'запись путей текущей библиотеки
   strCurBiblName = FormVyborBibl.LabelCurBiblName
   For i = 0 To UBound(Bibles)
      If Bibles(i).Name = strCurBiblName Then
         CurBibl = Bibles(i)
         Exit For
      End If
   Next
   'очищаем все что связано с библиотеками
   Set FormVyborBibl = Nothing
   Erase Bibles
   
   
'--------- Создание набора блоков изделий ----------
   
   'создание набора блоков
   'проверка, если уже есть такой набор в чертее, удаляем его
   Set objSelSet = Functions.GetSelSet("ЗаменаБлоков")
   Set objSelSetTemp = Functions.GetSelSet("Блоки_с_атрибутами")
   
   'вопрос, как выбирать элементы для спец., выбором рамкой или весь чертеж
   FormaSelectionSet.show
   
   pbInsertBlocksToLayerGBI = FormaSelectionSet.CheckBoxBlocksToLayerGBI.Value
   
   intFilterType(0) = 0: intFilterType(1) = 66
   varFilterDate(0) = "Insert": varFilterDate(1) = 1
   
      If bolAllorOnscreen = True Then 'выбираем весь чертеж
         objSelSetTemp.Select acSelectionSetAll, , , intFilterType, varFilterDate
      Else
         While intValue = 0 'пока выбранных элементов = 0, повторяем
            objSelSetTemp.SelectOnScreen intFilterType, varFilterDate
            intValue = objSelSetTemp.Count
         Wend
      End If
   
   'очищаем набор от ненужных блоков
   Set colBlockBrack = Nothing
   i = 0
   For Each objBlockRef In objSelSetTemp
    'фильтруем блоки Узлов
    If objBlockRef.Name <> "Узел" Then
      'в блоках жб изделий, должен быть атрибут на слое "Att~Material", и = "Железобетон"
      bolDaNet = False
      For Each varAtr In objBlockRef.GetAttributes
          Set objAttRef = varAtr
          If LCase(objAttRef.Layer) = "att~material" Then
            'проверяем значение атрибута
            If StrComp(LCase(objAttRef.TextString), "железобетон", vbTextCompare) = 0 Then 'если равен
               'значит это блок жб изделия
               Set objaBlockRef(0) = objBlockRef
               objSelSet.AddItems objaBlockRef
               bolDaNet = True 'типа это блок жб изделия
               Exit For
            End If
          End If
      Next
      'забракованные блоки (не жб изделия), заносим в набор
      If bolDaNet = False Then
         colBlockBrack.add objBlockRef ', CStr(i)
         'i = i + 1
      End If
    End If
   Next
   
   
'----- Процедура замены блоков ----------------
'   Dim dDoZB As Double
'   Dim dZB As Double
'   Dim dProvNalog As Double
'   dDoZB = Timer - Start
'   Start = Timer
   'замена блоков
   InsertBlockIzd 'процедура замещения блоков чертежа блоками из библиотеки
   'очищаем наложенные блоки при общей проверке
   Set colBlocksNalogenie = Nothing
   'проверяем наложенные блоки по BoundingBox
'   dZB = Timer - Start
'   Start = Timer
   ProvNalogenie 'проверка наложения блоков
'   dProvNalog = Timer - Start
'----- Завершение программы --------------

'   'реген
'   ThisDrawing.Regen (acActiveViewport) 'регенерация модели, обновить блоки
   
   'Восстановление состояния слоев
   Functions.LoadLayersSate
   
   Finish = Timer
   TotalTimeMin = FormatNumber((Finish - Start) / 60#, 2)
   
   FormaOtchet.LabelKolZB = "Количество замененных блоков жб изделий = " & intKolZB
   FormaOtchet.LabelTimer = "Время работы = " & TotalTimeMin & " мин."
   FormaOtchet.show vbModeless

Exit Sub
HasError:
   MsgBox Err.Description, vbCritical

Конец:
   'Восстановление состояния слоев
   Functions.LoadLayersSate

End Sub

'Private Sub ProvBlockAndAtr()
''процедура проверки блоков черетежа, на соответствие имени и их атрибутов (марки, видимого атрибута)
'
'   Dim ItemAcadObj As AcadObject
'   Dim objBlockRef As AcadBlockReference
'   Dim objBlock As AcadBlock
'   Dim strBlockName As String
'   Dim strNewBlockName As String
'   Dim varAttributes As Variant
'   Dim ItemObjAtr As Variant
'   Dim objAttr As AcadAttributeReference
'   Dim strValue As String
'   Dim strAtrTag As String
'   Dim strAtrText As String
'   Dim intOtvet As Integer
'   Dim intLen As Integer
'   Dim zcenter As Variant
'   Dim magnification As Double
'   Dim lCounter As Long
'
'   For Each objBlockRef In objSelSet 'перебор всех объектов набора
'         strBlockName = LCase(objBlockRef.Name) 'записываем имя блока, в нижнем регисте
'            varAttributes = objBlockRef.GetAttributes 'получаем список атрибутов
'            For Each ItemObjAtr In varAttributes
'               Set objAttr = ItemObjAtr
'               If objAttr.Invisible = False Then 'только для видимого атрибута
''                  strAtrTag = LCase(objAttr.TagString)
'                  strAtrText = LCase(objAttr.TextString)
''                  strValue = Left(strAtrText, 1)
''                  If strValue = "(" Then 'бывает атрибут марки в скобках "( )"
''                     intLen = Len(strAtrText)
''                     strAtrText = Left(strAtrText, intLen - 1)
''                     strAtrText = Right(strAtrText, intLen - 2)
''                  End If
'                  If StrComp(strAtrText, strBlockName, vbTextCompare) <> 0 Then 'если имя блока не равно имени атрибута
''                     If strAtrTag <> strAtrText Then  'если имя атрб не равно значению атрибута
'
'                              objBlockRef.Highlight True 'подсвечиваем
'
'                              magnification = 10000
'                              ZoomCenter objBlockRef.InsertionPoint, magnification
'
'                              intOtvet = MsgBox("В блоке с именем " & objBlockRef.Name & vbCrLf _
'                              & "Несовпадают: " & vbCrLf _
'                              & "Имя атрибута = " & objAttr.TagString & vbCrLf _
'                              & "Значение атрибута - " & objAttr.TextString & vbCrLf _
'                              & "Продолжить? Блок будет заменен библиотечным.", vbOKCancel)
'                              If intOtvet = 2 Then 'если нажали канцел, то выходим
'                                 End
'                              End If
'                              Exit For 'выходим из перебора атрибутов
''                     Else 'если имя и значение атриб совпадает, но имя блока не совпадает
''
''                              objBlockRef.Highlight True 'подсвечиваем
''                              magnification = 10000
''                              ZoomCenter objBlockRef.InsertionPoint, magnification
''
''                              intOtvet = MsgBox("В блоке с именем - " & objBlockRef.Name & vbCrLf _
''                              & "Несовпадают: " & vbCrLf _
''                              & "Имя и знач. атрибута - " & objAttr.TextString & vbCrLf _
''                              & "Продолжить? Блок будет заменен библиотечным.", vbOKCancel)
''                              If intOtvet = 2 Then 'если нажали канцел, то выходим
''                                 End
''                              End If
''                     End If
'                  End If
'               End If
'            Next
'   Next
'
'End Sub

'Private Sub ProvZerkalnost()
'
'   Dim ItemAcadObj As AcadObject
'   Dim objBlockRef As AcadBlockReference
'   Dim strBlockName As String
'   Dim lCounter As Long
'
'   For Each objBlockRef In objSelSet 'перебор всех объектов набора
'            strBlockName = objBlockRef.Name 'записываем имя блока, в нижнем регисте
'            If Sgn(objBlockRef.XScaleFactor) = -1 Or Sgn(objBlockRef.YScaleFactor) = -1 Then 'если отрицательное число, значит отзеркален
'               objBlockRef.Highlight True
'               ZoomCenter objBlockRef.InsertionPoint, 10000
'               MsgBox "Блок - " & strBlockName & " - отзеркален!" & vbCrLf _
'                     & "Исправте, и запускайте снова."
'               End
'            End If 'если отрицательное число
'   Next
'
'End Sub

'Private Sub ProvDublicatov()
'
'   Const Radius As Integer = 20 'точки вставки в радиусе 10мм
'   Const Radian As Double = 0.1 'поворот в пределах 5 градусов
'   Dim objBlockRef As AcadBlockReference
'   Dim objBlockRef2 As AcadBlockReference
'   Dim strBlockName As String
'   Dim strBlockName2 As String
'   Dim Pt1 As Variant
'   Dim rotation1 As Double
'   Dim Pt2 As Variant
'   Dim rotation2 As Double
'   Dim Id1 As Double
'   Dim Id2 As Double
'   Dim Cros1(2) As Double
'   Dim Cros2(2) As Double
'   Dim lCounter As Long
'   Dim lCounter2 As Long
'   Dim objSelSet2 As AcadSelectionSet
'   Dim intFilterType(2) As Integer
'   Dim varFilterDate(2) As Variant
'   Dim intOtvet As Integer
'   Dim vMinPt1 As Variant
'   Dim vMaxPt1 As Variant
'   Dim vMinPt2 As Variant
'   Dim vMaxPt2 As Variant
'   Dim bolNalogenie As Boolean
'
'   For Each objSelSet2 In ThisDrawing.SelectionSets
'      If objSelSet2.Name = "Вокруг блока" Then
'         objSelSet2.Delete
'         Exit For
'      End If
'   Next
'   Set objSelSet2 = ThisDrawing.SelectionSets.add("Вокруг блока")
'
'   For Each objBlockRef In objSelSet 'перебор всех объектов набора
'            strBlockName = objBlockRef.Name 'записываем имя блока
'            Id1 = objBlockRef.ObjectID
'            Pt1 = objBlockRef.InsertionPoint
'            rotation1 = objBlockRef.Rotation
'
'            'получаем границы первого блока
'            objBlockRef.GetBoundingBox vMinPt1, vMaxPt1
'
'            Cros1(0) = Pt1(0) - 7000: Cros1(1) = Pt1(1) - 7000: Cros1(2) = 0
'            Cros2(0) = Pt1(0) + 7000: Cros2(1) = Pt1(1) + 7000: Cros2(2) = 0
'
'            'фильтр блока по имени с атрибутом
'            intFilterType(0) = 0: intFilterType(1) = 2: intFilterType(2) = 66
'            varFilterDate(0) = "insert": varFilterDate(1) = strBlockName: varFilterDate(2) = 1
'
'            objSelSet2.Select acSelectionSetAll, Cros1, Cros2, intFilterType, varFilterDate
'
'            For Each objBlockRef2 In objSelSet2 'перебор всех объектов набора
'                     strBlockName2 = objBlockRef2.Name 'записываем имя блока
'                     Pt2 = objBlockRef2.InsertionPoint
'                     rotation2 = objBlockRef2.Rotation
'                     Id2 = objBlockRef2.ObjectID
'
'                  If Id1 <> Id2 Then
'                     'проверка наложения по границе
'                     'сравнение точек BoundingBox'оф
'                     'получаем границы блока
''                     objBlockRef2.GetBoundingBox vMinPt2, vMaxPt2
''                     If ProvBoundingBox(vMinPt1, vMinPt2, vMaxPt1, vMaxPt2) = True Then
''                        'заносим блок в колекцию (потенциально) наложенных блоков
''                        If intCountNalogenie = 0 Then
''                           Set colBlocksNalogenie = New Collection
''                        End If
''                        colBlocksNalogenie.add objBlockRef, CStr(intCountNalogenie)
''                        intCountNalogenie = intCountNalogenie + 1
'
''                        MsgBox "Наложение"
''                        GoTo Наложение
''                        bolNalogenie = True
''                     Else
''                        MsgBox "Все ок"
''                     End If
'
'                     If strBlockName2 = strBlockName And _
'                        rotation2 <= rotation1 + Radian And rotation2 >= rotation1 - Radian And _
'                        Pt2(0) >= Pt1(0) - Radius And Pt2(0) <= Pt1(0) + Radius And _
'                        Pt2(1) >= Pt1(1) - Radius And Pt2(1) <= Pt1(1) + Radius Then 'блоки накладываются
'
''                           objBlockRef.Highlight True
''                           objBlockRef2.Highlight True
''                           ZoomCenter Pt1, 10000
''                           intOtvet = MsgBox("Блок - " & strBlockName & " - дублируется (наложение блоков)!" & vbCrLf _
''                                 & "продолжить?", vbYesNo)
''                           If intOtvet = 7 Then 'нет
''                              End
''                           End If
''                           GoTo Наложение
'                           bolNalogenie = True
'                     End If ''блоки накладываются
'
'                     If bolNalogenie = True Then
'                        objBlockRef.Highlight True
'                        objBlockRef2.Highlight True
'                        ZoomCenter Pt1, 10000
'                        intOtvet = MsgBox("Блок - " & strBlockName & " - дублируется (наложение блоков)!" & vbCrLf _
'                           & "продолжить?", vbYesNo)
'                        If intOtvet = 7 Then 'нет
'                           End
'                        End If
'                     End If
'                  End If 'Id1 <> Id2 Then
'NextBlock:
'            Next 'lCounter = 1 To objSelSet.Count 'перебор всех объектов чертежа
'
'            objSelSet2.Clear
'   Next
'
'Exit Sub
'
''Наложение:
''   objBlockRef.Highlight True
''   objBlockRef2.Highlight True
''   ZoomCenter Pt1, 10000
''   intOtvet = MsgBox("Блок - " & strBlockName & " - дублируется (наложение блоков)!" & vbCrLf _
''      & "продолжить?", vbYesNo)
''   If intOtvet = 7 Then 'нет
''      End
''   End If
''   GoTo NextBlock
'
'End Sub

Private Sub ProvSelSetBlocksIzdel()
   'проверяем все блоки в наборе objSelSet на наличие и количество атрибутов
   
   Dim objBlockRef As AcadBlockReference
   Dim objItemAtr As AcadAttributeReference
   Dim varAtrCur As Variant
   Dim varItemAtr As Variant
   Dim bolYes As Boolean
   
   For Each objBlockRef In objSelSet
   
      'в блолке должно быть 5 атрибутов
      If objBlockRef.HasAttributes = False Then
         'нет атрибутов, ошибка, такого быть не должно
         objBlockRef.Highlight True
         ZoomCenter objBlockRef.InsertionPoint, 10000
         MsgBox "Блок изделия " & objBlockRef.Name & " без атрибутов!?. Выход."
         End
      Else
         varAtrCur = objBlockRef.GetAttributes 'получаем атрибуты текущего найденного блока
         If UBound(varAtrCur) <> 4 Then
            objBlockRef.Highlight True
            ZoomCenter objBlockRef.InsertionPoint, 10000
            MsgBox "В блоке изделия " & objBlockRef.Name & " - " & UBound(varAtrCur) + 1 & " атрибутов, а должно быть 5!?. Выход."
            End
         End If
         'проверка слоев атрибутов
         For Each varItemAtr In varAtrCur
            Set objItemAtr = varItemAtr
            Select Case objItemAtr.Layer
               Case "Att~Marka"
                  bolYes = True
               Case "Att~Naimen"
                  bolYes = True
               Case "Att~Obozn"
                  bolYes = True
               Case "Att~Massa"
                  bolYes = True
               Case "Att~Material"
                  bolYes = True
               Case Else
                  'нет атрибута на заданных слоях, ошибка, такого быть не должно
                  objBlockRef.Highlight True
                  ZoomCenter objBlockRef.InsertionPoint, 10000
                  MsgBox "В блоке " & objBlockRef.Name & " - ошибка в атрибутах!?. Выход."
                  End
            End Select
            If bolYes = False Then
               MsgBox "В блоке " & objBlockRef.Name & " - ошибка в атрибутах!?. Выход."
            End If
         Next
      End If
         
   Next
   
End Sub

Private Sub InsertBlockIzd()
   'вставка блоков изделий
   
   Dim objLayer As AcadLayer
   Dim strLayer As String
   Dim bolYes As Boolean
   Dim objBlock As AcadBlockReference
   
   'нужно проверить слой Att~Marka, на заблокирование
   For Each objLayer In ThisDrawing.Layers
      If objLayer.Name = "Att~Marka" Then
         objLayer.Lock = False
         If ThisDrawing.ActiveLayer.Name <> "Att~Marka" Then
           objLayer.Freeze = False
         End If
         objLayer.LayerOn = True
         Exit For
      End If
   Next
   'создание слоя блоков изделий
   'ищем слой
'   bolYes = False 'входное значение
'   For Each objLayer In ThisDrawing.Layers
'      If StrComp(objLayer.Name, strLayerBlockIzd) = 0 Then
'         bolYes = True
'         Exit For
'      End If
'   Next
'   If bolYes = False Then
'      'создаем слой
'      Set objLayer = ThisDrawing.Layers.add(strLayerBlockIzd)
'   End If
   If pbInsertBlocksToLayerGBI = True Then
      Set objLayer = Functions.GetLayer(strLayerBlockIzd)
      ThisDrawing.ActiveLayer = objLayer
   End If
  
   
   ReDim adDoInserta(objSelSet.Count - 1)
   ReDim adPosleInserta(objSelSet.Count - 1)
   
   'перебираем все выбранные блоки и заменяем на библиотечные
   For Each objBlock In objSelSet
      'процедура замены блока
      ZamenaBlocka objBlock
   Next
      
End Sub


Public Function SearchFileInBibl(FileName As String, objBlockRef As AcadBlockReference) As String  'возвращает строку полного пути к файлу
   'поиска файла в текущей библиотеки CurBibl
   
   Dim bolYes As Boolean
   Dim bolFindPath As Boolean
   Dim FindPath() As String
   Dim strPath As String
   Dim i As Integer
   Dim j As Integer
   Dim n As Integer
   Dim strValue As String
   Dim intValue As Integer
   Dim intOtvet As Integer
   Dim strFilePathInBibl As String
      
   'ищем файл в путях библиотеки
   For i = 0 To UBound(CurBibl.Paths)
      If CurBibl.Paths(i).IsFiles = True Then
         'поиск по дир
         strFilePathInBibl = CurBibl.Paths(i).path & "\" & FileName
         If Dir(strFilePathInBibl) <> "" Then
            ReDim Preserve FindPath(n)
            FindPath(n) = CurBibl.Paths(i).path
            bolFindPath = True 'что определен массив найденных путей
            n = n + 1
         End If
'         For j = 0 To UBound(CurBibl.Paths(i).FilesDwg)
'            If StrComp(CurBibl.Paths(i).FilesDwg(j), FileName, vbTextCompare) = 0 Then
'               ReDim Preserve FindPath(n)
'               FindPath(n) = CurBibl.Paths(i).Path
'               bolFindPath = True 'что определен массив найденных путей
'               n = n + 1
'            End If
'         Next
      End If
   Next
   
   'проверяем массив найденных путей
   If bolFindPath = True Then 'т.е. массив путей с найденым блоков в текущей библиотеке создан
      
      If UBound(FindPath) = 0 Then 'найден один путь
         'последний символ в пути должен быть "\"
         If Right(FindPath(0), 1) <> "\" Then
            FindPath(0) = FindPath(0) & "\"
         End If
         SearchFileInBibl = FindPath(0) & FileName
         Exit Function
         
      'если в массиве найденных путей не одна запись, то это нехорошо, будем проверять
      ElseIf UBound(FindPath) > 0 Then 'если больше 1 пути
         'т.е. в библиотеке блок найден на нескольких путях
         objBlockRef.Highlight True
         ZoomCenter objBlockRef.InsertionPoint, 10000
         'прописываем пути в листбокс
         For i = 0 To UBound(FindPath)
            FormaSupportPathFind.ListBoxFindPath.AddItem FindPath(i)
         Next
         FormaSupportPathFind.LabelName = FileName
         FormaSupportPathFind.show
         SearchFileInBibl = FormaSupportPathFind.ListBoxFindPath.Text & "\" & FileName
         Unload FormaSupportPathFind
         Exit Function
         
      End If
   'блок не найден в основной библиотеке, ищем в типовой
   Else  'если блок не найден в основной библиотеке, ищем в типовой
      If StandartBibl.IsPathes = True Then  'если есть пути в типовой библиотеке
         n = 0 'входное значение
         For i = 0 To UBound(StandartBibl.Paths)
          If StandartBibl.Paths(i).IsFiles = True Then
            'поиск по дир
            strFilePathInBibl = StandartBibl.Paths(i).path & "\" & FileName
            If Dir(strFilePathInBibl) <> "" Then
               ReDim Preserve FindPath(n)
               FindPath(n) = StandartBibl.Paths(i).path
               bolFindPath = True 'что определен массив найденных путей
               n = n + 1
            End If
'            For j = 0 To UBound(StandartBibl.Paths(i).FilesDwg)
'               If StrComp(StandartBibl.Paths(i).FilesDwg(j), FileName, vbTextCompare) = 0 Then
'                  ReDim Preserve FindPath(n)
'                  FindPath(n) = StandartBibl.Paths(i).Path
'                  bolFindPath = True
'                  n = n + 1
'               End If
'            Next
          End If
         Next
         'проверяем найденные пути с блоком в типовой библиотеке
         If bolFindPath = True Then 'массив путей определен
            If UBound(FindPath) = 0 Then 'найден один путь в типовой библиотеке
               'последний символ в пути должен быть "\"
               If Right(FindPath(0), 1) <> "\" Then
                  FindPath(0) = FindPath(0) & "\"
               End If
               SearchFileInBibl = FindPath(0) & FileName
               Exit Function
            
            'если в массиве найденных путей не одна запись, то это нехорошо, будем проверять
            ElseIf UBound(FindPath) > 0 Then 'если больше 1 пути
               'т.е. в типовой библиотеке блок найден на нескольких путях
               objBlockRef.Highlight True
               ZoomCenter objBlockRef.InsertionPoint, 10000
               'прописываем пути в листбокс
               For i = 0 To UBound(FindPath)
                  FormaSupportPathFind.ListBoxFindPath.AddItem FindPath(i)
               Next
               FormaSupportPathFind.LabelName = FileName
               FormaSupportPathFind.show
               SearchFileInBibl = FormaSupportPathFind.ListBoxFindPath.Text & FileName
               Unload FormaSupportPathFind
            End If
         Else 'блок не найден и в типовой библиотеке
            SearchFileInBibl = "" 'возвращаем пустую строчку
         End If
      Else 'если типовой библиотеки нет
         SearchFileInBibl = ""
      End If 'bolStandarBiblIs = True
   End If
   
End Function

Private Function ProvBlockIzdOnFreezeLayers() As Boolean
   'проверяем есть ли блоки изделий на замороженных слоях
   'true - продолжить программу
   'False - закончить программу
   
   Dim objLayer As AcadLayer
   Dim objSelSetFreeze As AcadSelectionSet
   Dim objBlockRef As AcadBlockReference
   Dim objAtt As AcadAttributeReference
   Dim intFilterType(2) As Integer
   Dim varFilterDate(2) As Variant
   Dim varAtt As Variant
   Dim intOtvet As Integer
   
   Dim aobjBlocksTemp() As AcadBlockReference
   Dim bolFreezeBlocks As Boolean
   Dim i As Integer
   Dim j As Integer
   
   'проверка, если уже есть такой набор в чертее, удаляем его
   Set objSelSetFreeze = Functions.GetSelSet("ЗамороженныеБлокиИзделий")
   
   'задаем фильтр блоков с атрибутами на заданном слое
   intFilterType(0) = 0: intFilterType(1) = 66: intFilterType(2) = 8
   varFilterDate(0) = "Insert": varFilterDate(1) = 1
   
   'находим заморженные слои и выбираем все блоки на этом слое
   For Each objLayer In ThisDrawing.Layers
      If objLayer.Freeze = True Then
         objLayer.Freeze = False
         varFilterDate(2) = objLayer.Name
         'выбираем все блоки на этом слое
         objSelSetFreeze.Clear
         objSelSetFreeze.Select acSelectionSetAll, , , intFilterType, varFilterDate
         'ищем блоки изделий в наборе
         i = 0
         For Each objBlockRef In objSelSetFreeze
            For Each varAtt In objBlockRef.GetAttributes
               Set objAtt = varAtt
               If LCase(objAtt.Layer) = "att~material" And StrComp(LCase(objAtt.TextString), "железобетон", vbTextCompare) = 0 Then
                  'значит это блок изделия, на замороженном слое (т.е. его не видно на экране)
                  ReDim Preserve aobjBlocksTemp(i)
                  Set aobjBlocksTemp(i) = objBlockRef 'записываем блок жб изделия на этом замороженном слое
                  i = i + 1
               End If
            Next
         Next 'objBlockRef In objSelSetFreeze
         'записываем блоки в массив замороженных блоков и слоев
            If i > 0 Then 'если найден хоть один блок на этом замороженном слое
               ReDim Preserve FreezeBlocks(j)
               FreezeBlocks(j).LayerName = objLayer.Name
               Set FreezeBlocks(j).colBlocks = New Collection
               For i = 0 To UBound(aobjBlocksTemp)
                  FreezeBlocks(j).colBlocks.add aobjBlocksTemp(i) ', CStr(i)
               Next
               FreezeBlocks(j).IsBlocks = True
               bolFreezeBlocks = True
               j = j + 1 'счетчик замороженных слоев с блоками жб изделий
            End If
      End If
   Next
   
   'выводим форму со списками замороженных слоев и блоков на них
   If bolFreezeBlocks = True Then
      'форма выводится в модальном режиме, с возможностью продолжения, при этом все слои обратно заморозятся,
      'и возможность завершения программы, м переключением этой формы в немодальный режим, для подробного просмотрка блоков
      ThisDrawing.Regen acActiveViewport
      FormaFreezeBlock.show
      If bolFreezeOk = True Then
         'продолжаем программу
         ProvBlockIzdOnFreezeLayers = True
      Else
         'заканчиваем программу
         ProvBlockIzdOnFreezeLayers = False
      End If
   Else
      ProvBlockIzdOnFreezeLayers = True
   End If
   
End Function

Private Sub ZamenaBlocka(objBlock As AcadBlockReference)
   'замена блока на чертеже библиотечным
   'записываем положение атрибута
   
   Dim objBlRefIzmPoint As AcadBlockReference
   Dim objInsertBlock As AcadBlockReference
   Dim objAtr As AcadAttributeReference
   Dim objLayer As AcadLayer
   Dim varAtrPt As Variant
   Dim varAtr As Variant
   Dim dAtrRot As Double
   Dim strLayer As String
   Dim strFileFullPath As String
   Dim intOtvet As Integer
   Dim i As Integer
   Dim bolYes As Boolean
   Dim vMinPt1 As Variant
   Dim vMaxPt1 As Variant
   Dim vMinPt2 As Variant
   Dim vMaxPt2 As Variant
   Dim intCountIzmPt As Integer
   Dim intCountNotFound As Integer
   Dim dXScale As Double
   Dim dYScale As Double
   
   Dim dStart As Double
   Dim dDoInsert As Double
   Dim dPosleInserta As Double
   
'   dStart = Timer

   Dim sBlLayerName As String
   
   sBlLayerName = objBlock.Layer
   Set objLayer = ThisDrawing.Layers.Item(objBlock.Layer)
   
   'Состояние слоя
   If pbInsertBlocksToLayerGBI = False Then
      If objLayer.Lock = True Then
          objLayer.Lock = False
      End If
      If objLayer.Freeze = True Then
          objLayer.Freeze = False
      End If
      If objLayer.LayerOn = False Then
          objLayer.LayerOn = True
      End If
   End If
   
   'получаем границы первого блока
   objBlock.GetBoundingBox vMinPt1, vMaxPt1

      For Each varAtr In objBlock.GetAttributes
'          Set objAtr = varAtr
          If varAtr.Layer = "Att~Marka" Then
            varAtrPt = varAtr.InsertionPoint
            dAtrRot = varAtr.Rotation
            Exit For
          End If
'          If objAtr.Layer = "Att~Material" Then
'            'проверяем значение атрибута
'            If StrComp(objAtr.TextString, "Железобетон", vbTextCompare) <> 0 Then 'если не жб
'               'значит это не блок изделия
'               'пропускаем блок, переходим к следущему
'               Exit Sub
'            End If
'          End If
      Next
'      'проверяем слой блока, чтобы его удалить, может и не нужно?????проверить
'      Set objLayer = ThisDrawing.Layers.Item(objBlock.Layer)
'      objLayer.Lock = False
'      'проверка замороженности и отключенности слоя актуальна для выбора всех блоко чертежа, кажется ?????
'      If Not objLayer Is ThisDrawing.ActiveLayer Then
'         objLayer.Freeze = False
'      End If
'      objLayer.LayerOn = True
      
      'находим путь к блоку в библиотеке
      strFileFullPath = SearchFileInBibl(objBlock.Name & ".dwg", objBlock)
      If strFileFullPath = "" Then 'значит файл не найден ни в основной ни в типовой библиотеках
         'заносим блок в коллекцию не найденных блоков в библиотеке
'         If intCountNotFound = 0 Then
'            Set colBlocksNotFound = New Collection
'         End If
         colBlocksNotFound.add objBlock ', CStr(intCountNotFound)
'         intCountNotFound = intCountNotFound + 1
         Exit Sub
      End If
      
'      dXScale = objBlock.XScaleFactor
'      dYScale = objBlock.YScaleFactor

'dDoInsert = Timer - dStart
'dStart = Timer
      
      Set objInsertBlock = ThisDrawing.ModelSpace.InsertBlock(objBlock.InsertionPoint, strFileFullPath, objBlock.XScaleFactor, objBlock.YScaleFactor, objBlock.ZScaleFactor, objBlock.Rotation)
      'подсчитываем кол-во замененных блоков
      intKolZB = intKolZB + 1
'      'переводим в слой блоков изделий
'      objInsertBlock.Layer = strLayerBlockIzd
      
'      objInsertBlock.XScaleFactor = dXScale
'      objInsertBlock.YScaleFactor = dYScale

      'Устанавливаем слой
      If pbInsertBlocksToLayerGBI = False Then
         objInsertBlock.Layer = sBlLayerName
      End If
      
      'устанавливаем положение атрибута
      For Each varAtr In objInsertBlock.GetAttributes
         Set objAtr = varAtr
         If objAtr.Layer = "Att~Marka" Then
            objAtr.Rotation = dAtrRot
            objAtr.Move objAtr.InsertionPoint, varAtrPt
            Exit For
         End If
      Next
      
      'проверяем не изменилась ли точка вставки,
      'измененные заносим в коллекцию измененных блоков
      'получаем границы вставленного блока
      objInsertBlock.GetBoundingBox vMinPt2, vMaxPt2
      If ProvBoundingBox(vMinPt1, vMinPt2, vMaxPt1, vMaxPt2, 1) = False Then
         'создаем коллекцию
'         If intCountIzmPt = 0 Then
'            Set colIzmInsertPoint = New Collection
'         End If
         'блоки не совпадают
         'заносим блоки в коллекцию с изменившейся точкой вставки
         colIzmInsertPoint.add objInsertBlock ', CStr(i)
         'intCountIzmPt = intCountIzmPt + 1
      End If
      
      'заносим замененный блок в коллекцию
      colZB.add objInsertBlock
      
      If objLayer.Lock = True Then
          objLayer.Lock = False
      End If
      objBlock.Delete 'удаляем старый блок

'dPosleInserta = Timer - dStart
'
'adDoInserta(intCount) = dDoInsert
'adPosleInserta(intCount) = dPosleInserta
'intCount = intCount + 1
   
End Sub

Private Function ProvBoundingBox(MinPt1 As Variant, MinPt2 As Variant, MaxPt1 As Variant, MaxPt2 As Variant, Dopusk As Integer) As Boolean
   'проверка наложенитя точек
   'наложение считается совпадение (в допусках) обоих точек BoundingBox
   'True - наложение
   
   'проверяем первую точку
   If MinPt2(0) < MinPt1(0) + Dopusk And MinPt2(0) > MinPt1(0) - Dopusk And _
       MinPt2(1) < MinPt1(1) + Dopusk And MinPt2(1) > MinPt1(1) - Dopusk Then
       'проверяем вторую точку
      If MaxPt2(0) < MaxPt1(0) + Dopusk And MaxPt2(0) > MaxPt1(0) - Dopusk And _
          MaxPt2(1) < MaxPt1(1) + Dopusk And MaxPt2(1) > MaxPt1(1) - Dopusk Then
          'значит точки лежат в пределах наложения, т.е. блоки накладываются
          ProvBoundingBox = True
      Else
         ProvBoundingBox = False
      End If
   Else
      ProvBoundingBox = False
   End If
   
End Function

Private Sub ProvNalogenie()
   'проверка блоков после ЗБ на наложение по BoundingBox

   'зона наложения
   Const intRadNalog As Integer = 100

   Dim objBlockRef As AcadBlockReference
   Dim objBlockRef2 As AcadBlockReference
   Dim Cros1(2) As Double
   Dim Cros2(2) As Double
   Dim oSelSet2 As AcadSelectionSet
   Dim intFilterType(1) As Integer
   Dim varFilterDate(1) As Variant
   Dim intOtvet As Integer
   Dim vMinPt1 As Variant
   Dim vMaxPt1 As Variant
   Dim vMinPt2 As Variant
   Dim vMaxPt2 As Variant
   Dim intCountNalogene As Integer
   
   ThisDrawing.Regen acActiveViewport
   
   Set oSelSet2 = Functions.GetSelSet("Вокруг блока")

   For Each objBlockRef In colZB 'перебор всех объектов набора
            'получаем границы первого блока
            objBlockRef.GetBoundingBox vMinPt1, vMaxPt1
            
'            Cros1(0) = objBlockRef.InsertionPoint(0) - 7000: Cros1(1) = objBlockRef.InsertionPoint(1) - 7000: Cros1(2) = 0
'            Cros2(0) = objBlockRef.InsertionPoint(0) + 7000: Cros2(1) = objBlockRef.InsertionPoint(1) + 7000: Cros2(2) = 0
            
            'фильтр блока по имени с атрибутом
            intFilterType(0) = 0: intFilterType(1) = 2
            varFilterDate(0) = "insert": varFilterDate(1) = objBlockRef.Name

            oSelSet2.Select acSelectionSetCrossing, vMinPt1, vMaxPt1, intFilterType, varFilterDate
            
            For Each objBlockRef2 In oSelSet2 'перебор всех объектов набора
               If Not objBlockRef2 Is objBlockRef Then
                     'проверка наложения по границе
                     'сравнение точек BoundingBox'оф
                     'получаем границы блока
                     objBlockRef2.GetBoundingBox vMinPt2, vMaxPt2
                     If ProvBoundingBox(vMinPt1, vMinPt2, vMaxPt1, vMaxPt2, intRadNalog) = True Then
                        'заносим блок в колекцию (потенциально) наложенных блоков
                        colBlocksNalogenie.add objBlockRef, CStr(intCountNalogene)
                        intCountNalogene = intCountNalogene + 1
                     End If
               End If 'Id1 <> Id2 Then
            Next 'lCounter = 1 To objSelSet.Count 'перебор всех объектов чертежа

            oSelSet2.Clear
   Next

End Sub

Private Sub AllProverks()
   'все проверки блоков, зеркальность, наложение, видимого атрибута
   
   'зона наложения
   Const intRadNalog As Integer = 100
   
   Dim objBlockRef As AcadBlockReference
   Dim objBlockRef2 As AcadBlockReference
   Dim objAttr As AcadAttributeReference
   Dim objSelSet2 As AcadSelectionSet
   Dim Cros1(2) As Double
   Dim Cros2(2) As Double
   Dim intFilterType(2) As Integer
   Dim varFilterDate(2) As Variant
   Dim vMinPt1 As Variant
   Dim vMaxPt1 As Variant
   Dim vMinPt2 As Variant
   Dim vMaxPt2 As Variant
   Dim varAttributes As Variant
   Dim intOtvet As Integer
   Dim bolMaterial As Boolean
   
   Set objSelSet = Functions.GetSelSet("Проверка")
   
   'фильтр блоков  с атрибутом
   intFilterType(0) = 0: intFilterType(1) = 66: intFilterType(2) = 66
   varFilterDate(0) = "insert": varFilterDate(1) = 1: varFilterDate(2) = 1
   
   objSelSet.Select acSelectionSetAll, , , intFilterType, varFilterDate

   'создаем вспомогательный набор
   Set objSelSet2 = Functions.GetSelSet("Вокруг блока")
   
   ZoomAll
   
   'фильтр блока по имени с атрибутом
   intFilterType(0) = 0: intFilterType(1) = 2: intFilterType(2) = 66
   varFilterDate(0) = "insert": varFilterDate(2) = 1
   
   'перебор всех объектов набора
   For Each objBlockRef In objSelSet
    If objBlockRef.Name <> "Узел" Then
      'проверка зеркальности
      If objBlockRef.XScaleFactor < 0 Or objBlockRef.YScaleFactor < 0 Then 'если отрицательное число, значит отзеркален
         'добавляем блок в коллекцию зеркальных блоков
         colBlocksZerkal.add objBlockRef
         bolProverka = True
      End If 'если отрицательное число
      
      'проверка наложения
      'получаем границы первого блока
      objBlockRef.GetBoundingBox vMinPt1, vMaxPt1
'      'задаем точки выбора для рамки вокруг блока
'      Cros1(0) = objBlockRef.InsertionPoint(0) - 7000: Cros1(1) = objBlockRef.InsertionPoint(1) - 7000: Cros1(2) = 0
'      Cros2(0) = objBlockRef.InsertionPoint(0) + 7000: Cros2(1) = objBlockRef.InsertionPoint(1) + 7000: Cros2(2) = 0
      'фильтр блока по имени с атрибутом
       varFilterDate(1) = objBlockRef.Name
      'выбираем
      objSelSet2.Select acSelectionSetCrossing, vMinPt1, vMaxPt1, intFilterType, varFilterDate
      'перебираем эти блоки вокруг блока
      For Each objBlockRef2 In objSelSet2 'перебор всех объектов набора
         If Not objBlockRef2 Is objBlockRef Then  'проверяем что бы это не было objBlockRef is objBlockRef2
            objBlockRef2.GetBoundingBox vMinPt2, vMaxPt2
            If ProvBoundingBox(vMinPt1, vMinPt2, vMaxPt1, vMaxPt2, intRadNalog) = True Then
               'добавляем блок в коллекцию дублирующихся блоков
               colBlocksNalogenie.add objBlockRef
               bolProverka = True
            End If
         End If
      Next
      objSelSet2.Clear
      
      'проверка имени блока и атрибута марки
      bolMaterial = False
      For Each varAttributes In objBlockRef.GetAttributes
         Set objAttr = varAttributes
         If LCase(objAttr.Layer) = "att~marka" Then 'атрибут марки должен быть на слое Att~Marka
            'если имя блока не равно имени атрибута
            If StrComp(objAttr.TextString, objBlockRef.Name, vbTextCompare) <> 0 Then
               colBlocksErrName.add objBlockRef
               bolProverka = True
            End If
         End If
         If LCase(objAttr.Layer) = "att~material" Then
'            If LCase(objAttr.TextString) <> "железобетон" Then
'               colBlockBrack.add objBlockRef
'               bolProverka = True
'            End If
            bolMaterial = True
         End If
      Next
      If bolMaterial = False Then
         'если нет атрибута на слое "att~material", значит это неопределенный блок
         colBlockBrack.add objBlockRef
      End If
    End If
   Next 'objBlockRef In objSelSet
   
End Sub

Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit


Public Sub InsertProblemsBlock()
   'проблема с атрибутами нескольких блоков,
   'нужно вместо них вставить блоки из библиотеки
   'ФБС12.6.3-Т
   'ФБС12.4.3-Т
   'ЦВ6 -1
   
   Dim objSelSet As AcadSelectionSet
   Dim intFilterType(1) As Integer
   Dim varFilterDate(1) As Variant
   Dim objBlock As AcadBlockReference
   Dim dAtrRot As Double
   Dim dPt(2) As Double
   Dim dAtrPt(0 To 2) As Double
   
   
   Dim objInsertBlock As AcadBlockReference
   Dim objAtr As AcadAttributeReference
   Dim varAtrPt As Variant
   Dim varAtr As Variant
   
'   Set objInsertBlock = ThisDrawing.ModelSpace.InsertBlock(dPt, "ФБС12.6.3-Т", 1, 1, 1, 0)
'   ZoomCenter objInsertBlock.InsertionPoint, 10000
'   varAtrPt = Utility.GetPoint
'   For Each varAtr In objInsertBlock.GetAttributes
'      Set objAtr = varAtr
'      If objAtr.Layer = "Att~Marka" Then
'         objAtr.InsertionPoint = varAtrPt
'         objAtr.Update
'      End If
'   Next
   
      
   For Each objSelSet In ThisDrawing.SelectionSets
      If objSelSet.Name = "ЗаменаБлоков" Then
         objSelSet.Delete
         Exit For
      End If
   Next
   
   'добавляем набор в коллекцию наборов этого чертежа
   Set objSelSet = ThisDrawing.SelectionSets.add("ЗаменаБлоков")
      
   intFilterType(0) = 0: intFilterType(1) = 66 ': intFilterType(2) = 2
   varFilterDate(0) = "Insert": varFilterDate(1) = 1 ': varFilterDate(2) = "ФБС12.4.3-Т" 'ФБС12.6.3-Т, ФБС12.4.3-Т, ЦВ6 -1
   
   objSelSet.Select acSelectionSetAll, , , intFilterType, varFilterDate
   
   For Each objBlock In objSelSet
      'записываем его положение
'      objBlock.Highlight True
'      ZoomCenter objBlock.InsertionPoint, 10000
      For Each varAtr In objBlock.GetAttributes
          Set objAtr = varAtr
          If objAtr.Layer = "Att~Marka" Then
            varAtrPt = objAtr.InsertionPoint
            dAtrRot = objAtr.Rotation
          End If
      Next
      Set objInsertBlock = ThisDrawing.ModelSpace.InsertBlock(objBlock.InsertionPoint, objBlock.Name & ".dwg", 1, 1, 1, objBlock.Rotation)
      For Each varAtr In objInsertBlock.GetAttributes
         Set objAtr = varAtr
         If objAtr.Layer = "Att~Marka" Then
            objAtr.Rotation = dAtrRot
            objAtr.Move objAtr.InsertionPoint, varAtrPt
'            objAtr.InsertionPoint = varAtrPt
            objAtr.Update
         End If
      Next
      objBlock.Delete
   Next
   
End Sub


Sub NewInsertPoint()
    Dim Object As Object
    Dim PickedPoint As Variant, TransMatrix As Variant, ContextData As Variant

    ThisDrawing.Utility.GetSubEntity Object, PickedPoint, TransMatrix, ContextData

    Dim objAtt As AcadAttributeReference
    Dim varPt As Variant

    varPt = ThisDrawing.Utility.GetPoint(, "Enter a point: ")

    Set objAtt = Object
    
    objAtt.InsertionPoint = varPt
    ThisDrawing.Regen acActiveViewport
    
End Sub


Private Sub Preference()
   
   Dim strSup As String
   Dim PrefFiles As AcadPreferencesFiles
   Dim bolYes As Boolean
   Dim Sup() As String
   Dim i As Integer
   Dim intVal As Integer
   Dim intVal2 As Integer
   Dim intLen As Integer
   
   Set PrefFiles = AutoCAD.Preferences.Files
   
   strSup = PrefFiles.SupportPath
   intLen = Len(strSup)
   ReDim Preserve Sup(i) As String
   
   While bolYes = False
      intVal = InStr(strSup, ";")
      If intVal = 0 Then
         Sup(i) = strSup
         bolYes = True
      Else
         Sup(i) = Mid(strSup, 1, intVal - 1)
         i = i + 1
         ReDim Preserve Sup(i) As String
         strSup = Mid(strSup, intVal + 1)
         intVal = InStr(strSup, ";")
         If Sup(i - 1) = "" Then
            bolYes = True
         End If
      End If
   Wend
   
   Dim strFiles As String
   
   strSup = Sup(9)
   strFiles = Dir(strSup & "\")
   Dim R As Integer
   Dim strF() As String
   Do While strFiles <> ""
        
        ReDim Preserve strF(R) As String
        strF(R) = strFiles
        'Получение следующего файла
        strFiles = Dir
        R = R + 1
    Loop
   
End Sub


Public Sub ini()
   
   Dim strValue As String
   Dim strPath As String
   
   strPath = "D:\Vildar\Разное\2"

   'нужно проверить существование пути
   strValue = Dir(strPath, vbDirectory)
   
End Sub

Public Sub Тест_размерности_массива()
   
   Dim i As Integer
   Dim j As Integer
   Dim strArr() As String
   Dim strArrTemp() As String
      
   ReDim strArr(1, 2) As String
   
   For i = 0 To 1
      For j = 0 To 2
         strArr(i, j) = i + j
      Next
   Next
   'переопределяем массив через временный массив
   ReDim strArrTemp(2, 2) As String
   For i = 0 To 1
      For j = 0 To 2
         strArrTemp(i, j) = strArr(i, j)
      Next
   Next
   ReDim strArr(2, 2) As String
   strArr = strArrTemp
   
End Sub


Sub ReadTabulatedData()
   Dim coll As New Collection
   Dim stroka, tmparr
   ' открываем файл для чтения (измени полный путь файла):
   Open "\\Sgpsrv2\СПД\Конструкторы\Макросы\Замена блоков\data.txt" For Input As #1
   Line Input #1, stroka   ' считываем строку в переменную
   ' считываем построчно до конца файла:
   Do While Not EOF(1)
      tmparr = Split(stroka, " ")
   ' заполняем коллекцию (поскольку не знаем количество строк):
   coll.add tmparr
   Line Input #1, stroka   ' считываем строку в переменную в продолжении цикла
   Loop
   ' закрываем файл
   Close #1
   ' конвертируем коллекцию в двумерный массив 'ar'
   ReDim ar(0 To coll.Count - 1, 0 To UBound(coll.Item(1)))
   Dim i, j
   For i = 1 To UBound(ar, 1) + 1
   For j = 0 To UBound(ar, 2)
   ar(i - 1, j) = coll.Item(i)(j)
   Next
   Next
   ' << далее работаешь с массивом >>
End Sub

Sub Example_CellMerge()

   Dim MyModelSpace As AcadModelSpace
   Set MyModelSpace = ThisDrawing.ModelSpace
   Dim pt(2) As Double
   Dim MyTable As AcadTable
   
   Set MyTable = MyModelSpace.AddTable(pt, 5, 5, 10, 30)
   Call MyTable.MergeCells(3, 4, 3, 4)
   
   ZoomExtents

End Sub
