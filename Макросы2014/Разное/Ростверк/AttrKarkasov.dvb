Attribute VB_Name = "FormaProverky"
Attribute VB_Base = "0{E0175262-1B0A-4217-972A-BCE100893FE7}{20996738-35C1-49C4-95C7-A820C2B5778D}"
Attribute VB_GlobalNameSpace = False
Attribute VB_Creatable = False
Attribute VB_PredeclaredId = True
Attribute VB_Exposed = False
Attribute VB_TemplateDerived = False
Attribute VB_Customizable = False

Option Explicit
   
   'тип текущего списка блоков
   Enum ListBoxType
      NotConstr = 0
      NotMassa = 1
      Other = 2
      Zerkal = 3
   End Enum
   
   Dim intListBoxType As Integer

Private Sub cmbNotMassa_Click()
   Dim objBlock As AcadBlockReference
   
   ListBoxBlocks.Clear
   
   'вывести список неопределенных блоков
   For Each objBlock In colBlNotMassa
      'надеюсь индексы совпадут ????????????????
      ListBoxBlocks.AddItem objBlock.Name
   Next
   
   LabelPrimech = "Без массы"
   
   intListBoxType = ListBoxType.NotMassa
   
End Sub

Private Sub cmbExit_Click()
   End
End Sub

'Private Sub cmbOK_Click()
'   'все по новой
'
'   Dim bolYes As Boolean
'   Dim bolMaterial As Boolean
'   Dim objBlRef As AcadBlockReference
'   Dim varAtr As Variant
'
'   bolProverka = True
'
'   If MsgBox("Продолжить замену блоков?", vbQuestion + vbYesNo) = vbNo Then
'      Exit Sub
'   End If
'
'   If bolYes = True Then
'      cmbView.Enabled = True
'   End If
'
'   'если были неопределенные блоки делаем их определенными (атрибут Материал=Железобетон)
'   If colBlockBrack.Count <> 0 Then
'      For Each objBlRef In colBlockBrack
'         For Each varAtr In objBlRef.GetAttributes
'            If LCase(varAtr.Layer) = "att~material" Then
'               varAtr.TextString = "Железобетон"
'               bolMaterial = True
'               Exit For
'            End If
'         Next
'         'если нет атрибута на слое "Att~Material", может есть атрибут = "железобетон"
'         If bolMaterial = False Then
'            For Each varAtr In objBlRef.GetAttributes
'               If LCase(varAtr.TextString) = "железобетон" Then
'                  'переводим атрибут на слой материала
'                  varAtr.Layer = "Att~Material"
'                  Exit For
'               End If
'            Next
'         End If
'      Next
'   End If
'
'   hide
'End Sub

Private Sub cmbNotConstr_Click()
   
   Dim objBlock As AcadBlockReference
   
   ListBoxBlocks.Clear
   
   'вывести список неопределенных блоков
   For Each objBlock In colBlNotConstr
      'надеюсь индексы совпадут ????????????????
      ListBoxBlocks.AddItem objBlock.Name
   Next
   
   intListBoxType = ListBoxType.NotConstr
   
   LabelPrimech = "Без Конструкция=Ростверк"
   
End Sub

'Private Sub cmbStop_Click()
'   bolProverka = False
'   cmbOK.Visible = False
'   cmbStop.Visible = False
'   cmbExit.Visible = True
'   hide
'   FormaProverky.Show vbModeless
'End Sub

Private Sub cmbView_Click()
   
   Dim objBlock As AcadBlockReference
   Dim index As Integer
   
   On Error GoTo HasError
   
   index = ListBoxBlocks.ListIndex
   If index = -1 Then
      Exit Sub
   End If
   
   index = index + 1
   Select Case intListBoxType
      Case ListBoxType.NotConstr
         Set objBlock = colBlNotConstr.Item(index)
      Case ListBoxType.NotMassa
         Set objBlock = colBlNotMassa.Item(index)
      Case ListBoxType.Other
         Set objBlock = colOtherBl.Item(index)
      Case ListBoxType.Zerkal
         Set objBlock = colZerkalBl.Item(index)
   End Select
   
   objBlock.Highlight True
   ZoomCenter objBlock.InsertionPoint, 10000

Exit Sub
HasError:
   Select Case Err.Number
      Case -2145386420
         MsgBox "Блок был удален", vbCritical
         Select Case intListBoxType
            Case ListBoxType.NotConstr
               colBlNotConstr.Remove (index)
            Case ListBoxType.NotMassa
               colBlNotMassa.Remove (index)
            Case ListBoxType.Other
               colOtherBl.Remove (index)
            Case ListBoxType.Zerkal
               colZerkalBl.Remove (index)
         End Select
         ListBoxBlocks.RemoveItem index - 1
      Case Else
         MsgBox Err.Description, vbCritical
   End Select

End Sub

Private Sub cmbOtherBl_Click()
   Dim objBlock As AcadBlockReference
   
   ListBoxBlocks.Clear
   
   'вывести список неопределенных блоков
   For Each objBlock In colOtherBl
      'надеюсь индексы совпадут ????????????????
      ListBoxBlocks.AddItem objBlock.Name
   Next
   
   LabelPrimech = "Остальные блоки, без буквы К"
   
   intListBoxType = ListBoxType.Other
   
End Sub

Private Sub cmbZerkal_Click()
   Dim objBlock As AcadBlockReference
   
   ListBoxBlocks.Clear
   
   'вывести список неопределенных блоков
   For Each objBlock In colZerkalBl
      'надеюсь индексы совпадут ????????????????
      ListBoxBlocks.AddItem objBlock.Name
   Next
   
   LabelPrimech = "Зеркальные"
   
   intListBoxType = ListBoxType.Zerkal
End Sub

Private Sub CommandButton1_Click()
   hide
   Me.Show vbModeless
End Sub

Private Sub UserForm_Activate()
   'проверяем коллекции блоков с ошибками и отображаем кнопки
   
   Dim bolYes As Boolean
   
   If colBlNotConstr.Count <> 0 Then
      'показываем кнопку
      cmbNotConstr.Visible = True
      bolYes = True
      'отсортировать блоки в коллекции
      Call LibFunctions.SortyrBlInCol(colBlNotConstr)
   End If
   If colBlNotMassa.Count <> 0 Then
      'показываем кнопку
      cmbNotMassa.Visible = True
      bolYes = True
      'отсортировать блоки в коллекции
      Call LibFunctions.SortyrBlInCol(colBlNotMassa)
   End If
   If colOtherBl.Count <> 0 Then
      'показываем кнопку
      cmbOtherBl.Visible = True
      bolYes = True
      'отсортировать блоки в коллекции
      Call LibFunctions.SortyrBlInCol(colOtherBl)
   End If
   If colZerkalBl.Count <> 0 Then
      'показываем кнопку
      cmbZerkal.Visible = True
      bolYes = True
      'отсортировать блоки в коллекции
      Call LibFunctions.SortyrBlInCol(colZerkalBl)
   End If
   
   If bolYes = True Then
      cmbView.Enabled = True
   End If
   
End Sub

Attribute VB_Name = "LibFunctions"
Option Explicit

Public Function GetMacroFolder(strVBProjectName) As String
   'получение пути к корню макроса
   'без \
   
   Dim strMacroFolder As String
   Dim intValue As Integer
   
   On Error GoTo HasError
   
   strMacroFolder = Application.VBE.vbprojects.Item(strVBProjectName).FileName
   intValue = InStrRev(strMacroFolder, "\")
   strMacroFolder = Left(strMacroFolder, intValue - 1) 'корень с макросом, без \ на конце
   
   GetMacroFolder = strMacroFolder
   
Exit Function

HasError:
   Select Case Err.Number
      Case Else
         MsgBox "Functions, GetMacroFolder" & vbCrLf & _
               Err.Description
   End Select
   
End Function

Public Function GetColShifFromTXT() As Collection
   'считываем строки из файла и заполняем коллекцию объектами шифра
   
   'пока жестко установлю путь к файлу с шифрами
   'но когда придумаю где сохранять путь к макросам (реестр, или ини) то нужно будет считываать оттуда
   Const ShifrTXTFullPath As String = "\\Sgpsrv2\СПД\Конструкторы\Макросы\Шифры\Shifr.txt"
   
   Dim colShifr As New Collection
   Dim objShifr As clShifr
   Dim strShifr As String
   Dim strValue As String
   Dim intValue As Integer
   
   'форма записы шифра:
   '3085-10;Купряхин А.П.;ЗАО"Кронверк-3";Шурова Гора 7, в Ленинском районе г.Саратова;Жилой дом №10
   
   If Dir(ShifrTXTFullPath) = "" Then
      'возвращаем Nothing
      Exit Function
   End If
   
   Close #1
   'через открытие файла
   Open ShifrTXTFullPath For Input Access Read As #1
   'чтение файла
   While Not EOF(1)
      Set objShifr = New clShifr
      Line Input #1, strShifr
      'до первого ; - шифр
      intValue = InStr(strShifr, ";")
      strValue = Left(strShifr, intValue - 1)
      objShifr.Shifr = strValue
      strShifr = Mid(strShifr, intValue + 1) 'сокращаем строчку до первого ; включительно
      'до второго ; - бс
      intValue = InStr(strShifr, ";")
      strValue = Left(strShifr, intValue - 1)
      objShifr.BS = strValue
      strShifr = Mid(strShifr, intValue + 1)
      'до след ; - часть
      intValue = InStr(strShifr, ";")
      strValue = Left(strShifr, intValue - 1)
      objShifr.Part = strValue
      strShifr = Mid(strShifr, intValue + 1)
      'до след ; - ГИП
      intValue = InStr(strShifr, ";")
      strValue = Left(strShifr, intValue - 1)
      objShifr.GIP = strValue
      strShifr = Mid(strShifr, intValue + 1)
      'след ; - заказчик
      intValue = InStr(strShifr, ";")
      strValue = Left(strShifr, intValue - 1)
      objShifr.Clients = strValue
      strShifr = Mid(strShifr, intValue + 1)
      'след ; - адресс
      intValue = InStr(strShifr, ";")
      strValue = Left(strShifr, intValue - 1)
      objShifr.Adress = strValue
      strShifr = Mid(strShifr, intValue + 1)
      'след ; - наименование объекта
      intValue = InStr(strShifr, ";")
      strValue = Left(strShifr, intValue - 1)
      objShifr.ObjectName = strValue
      strShifr = Mid(strShifr, intValue + 1)
      'след ; - должность нач.отдела
      intValue = InStr(strShifr, ";")
      strValue = Left(strShifr, intValue - 1)
      objShifr.FieldNachOtd = strValue
      strShifr = Mid(strShifr, intValue + 1)
      'след ;  - фамилия нач.отдела
      intValue = InStr(strShifr, ";")
      strValue = Left(strShifr, intValue - 1)
      objShifr.FamNachOtd = strValue
      strShifr = Mid(strShifr, intValue + 1)
      'след фамилия Гл.специалиста
      objShifr.GlSpec = strShifr
      'добавляем объект в коллекцию
      colShifr.Add objShifr, objShifr.Shifr
   Wend
   Close #1
   
   Set GetColShifFromTXT = colShifr
   
End Function

Public Function GetColGIPFromTXT(GIPTxtFullPath As String) As Collection
   'считываем гипов из файла
   'заполняем массив из типов по гипавм
   
   Dim colGIP As New Collection
   Dim objGIP As clGIP
   Dim strGIP As String
   Dim intValue As Integer
   
   'форма записы ГИПа:
   'Купряхин С.П.
   
   If Dir(GIPTxtFullPath) = "" Then
      'возвращаем Nothing
      Exit Function
   End If
   
   Close #1
   'открываем файл для чтения
   Open GIPTxtFullPath For Input Access Read As #1
   'чтение файла
   While Not EOF(1)
      Set objGIP = New clShifr
      Line Input #1, strGIP
      'пока только одна запись в строчке - Фамилия И.О.
      objGIP.FamilIO = strGIP
      'добавляем объект в коллекцию
      'проверка на ошибку совпадении ключей, при добавлении нового гипа в коллекцию ?????????
      colGIP.Add objGIP, objGIP.FamilIO
   Wend
   Close #1
   
   Set GetColGIPFromTXT = colGIP
   
End Function

Public Function GetColClientFromTXT(ClientTxtFullPath As String) As Collection
   'считываем заказчиков из файла
   'заполняем массив из типов по заказчикам
   
   Dim colClient As New Collection
   Dim objClient As clClient
   Dim strClient As String
   Dim intValue As Integer
   
   'форма записы заказчика:
   'ЗАО"Кронверк-3"
   
   If Dir(ClientTxtFullPath) = "" Then
      'возвращаем Nothing
      Exit Function
   End If
   
   Close #1
   'открываем файл для чтения
   Open ClientTxtFullPath For Input Access Read As #1
   'чтение файла
   While Not EOF(1)
      Set objClient = New clClient
      Line Input #1, strClient
      'пока только одна запись в строчке - название фирмы
      objClient.Firma = strClient
      'добавляем объект в коллекцию
      'проверка на ошибку совпадении ключей, при добавлении нового заказчика в коллекцию ?????????
      colClient.Add objClient, objClient.Firma
   Wend
   Close #1
   
   Set GetColClientFromTXT = colClient
   
End Function

Public Function GetShifrFromDict() As String
   'чтение записи шифра из словаря
   'словарь SPD
   'запись Shifr
   'если нет словаря или записи, возвращает ""
   
   Dim objDict As AcadDictionary
   Dim objXRec As AcadXRecord
   Dim XRDataType As Variant
   Dim XRDataValue As Variant
   
   On Error GoTo HasError
   
   'получаем словарь чертежа
   Set objDict = ThisDrawing.Dictionaries.Item("SPD")
   'получаем запись SPD из словаря
   Set objXRec = objDict.Item("Shifr")
   'считываем данные записи
   objXRec.GetXRecordData XRDataType, XRDataValue
   
   If IsEmpty(XRDataValue) = True Then
      GetShifrFromDict = ""
      Exit Function
   Else
      GetShifrFromDict = XRDataValue(0)
      Exit Function
   End If

Exit Function

'обработка шибок
HasError:
   Select Case Err.Number
      Case -2145386476 'Ключ не найден
         'если нет записи
         'возвращаем пустую строчку
'         MsgBox "Ключ не найден"
         GetShifrFromDict = ""
         Exit Function
      Case Else
         MsgBox "Функция GetShifrFromDict - " & Err.Description
         GetShifrFromDict = ""
         Exit Function
   End Select
   
Resume Next
   
End Function

Public Function SetShifrToDict(strShifr As String) As Boolean
   'запись шифра в словарь
   'словарь SPD
   'запись Shifr
   
   Dim objDict As AcadDictionary
   Dim objXRec As AcadXRecord
   Dim XRDataType(0) As Integer
   Dim XRDataValue(0) As Variant
   
   On Error GoTo HasError
   
   'получаем словарь
   Set objDict = ThisDrawing.Dictionaries.Item("SPD")
   If objDict Is Nothing Then
      'нет словаря в чертеже, создаем
      Set objDict = ThisDrawing.Dictionaries.Add("SPD")
   End If
   
   Set objXRec = objDict.Item("Shifr")
   If objXRec Is Nothing Then
      'если нет записы, создаем
      Set objXRec = objDict.AddXRecord("Shifr")
   End If
   
   XRDataType(0) = 1
   XRDataValue(0) = strShifr
    
   'записываем в XRecord словаря
   objXRec.SetXRecordData XRDataType, XRDataValue
   
   SetShifrToDict = True

Exit Function

'обработка шибок
HasError:
   Select Case Err.Number
      Case "-2145386476" 'Ключ не найден
         'если словаря или записи, продолжаем, там далее идет создание
         Resume Next
      Case Else
         MsgBox "Err.Description - " & Err.Description
         SetShifrToDict = False
         Exit Function
   End Select
     
End Function

Public Function GetColBlockName(strBlockName As String) As Collection
   'возвращает коллекцию блоков заданного имиени в черткеже
   
   Dim selBlocks As AcadSelectionSet
   Dim objBlockRef As AcadBlockReference
   Dim intFT(1) As Integer
   Dim varFD(1) As Variant
   
   'создаем набор
   Set selBlocks = GetNewSelSet("Блоки")
   
   'задаем фильтр
   intFT(0) = 0: varFD(0) = "insert"
   intFT(1) = 2: varFD(1) = strBlockName
   
   selBlocks.Select acSelectionSetAll, , , intFT, varFD
   
   If selBlocks.Count = 0 Then
      Set GetColBlockName = Nothing
   Else
      Set GetColBlockName = New Collection
      For Each objBlockRef In selBlocks
         GetColBlockName.Add objBlockRef
      Next
   End If
   
End Function

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function GetFamilWithoutInitial(strFamil As String) As String
   'возвращает строку фамилии без инициалов
   'разделителем фамилии и инициалов может быть или " " или прописная буква
   
   Dim intLen As Integer
   Dim strSymbol As String
   Dim i As Integer
   
   intLen = InStr(strFamil, " ")
   
   'если есть пробел, то значит это пробел между фамилией и инициалами
   If intLen <> 0 Then
      GetFamilWithoutInitial = Left(strFamil, intLen - 1)
   Else
      GetFamilWithoutInitial = strFamil
   End If
   
End Function

Public Function CheckAccessToShifrTxt() As String
   'проверка редактирется ли каталог шифров сейчас
   'определяется наличием файла "Shifr_Edit.txt", рядом с основным txt
   'возвращает имя компа - если база редактруется сейчас
   'или "" если доступ свободен
   
   Dim strShifrEditTxt As String
   
   strShifrEditTxt = GetMacroFolder & "\Shifr_Edit.txt"
   'проверяем наличие файла "Shifr_Edit.txt"
   If Dir(strShifrEditTxt) = "" Then
      CheckAccessToShifrTxt = ""
   Else
      'определяем имя компа, т.е. считываем первую строчку
      'открываем файл для чтения
      Open strShifrEditTxt For Input Access Read As #1
      'считываем первую строчку
      Line Input #1, CheckAccessToShifrTxt
      'закрываем файл
      Close #1
   End If
   
End Function

Public Function OpenAccessToShifrTxtYesNo() As Boolean
   'создаем скрытый файл, только для чтения "Shifr_Edit.txt"
   
   Dim strShifrEditTxt As String
   Dim strKompName As String
   
   'имя этого компъютера в сети
   strKompName = WinAPI.ComputerName
   
   'файл для создания
   strShifrEditTxt = GetMacroFolder & "\Shifr_Edit.txt"
   'открываем скрытый файл для записи
   Open strShifrEditTxt For Output Lock Write As #1
      Print #1, strKompName
   Close #1
   
   OpenAccessToShifrTxtYesNo = True
   
End Function


Public Function AddBlocksFromDWG(strDwgFileFullPath) As Boolean
   'внедрение определений блоков из внешнего файла в текущий чертеж
   
   Dim dPt(2) As Double
   Dim objXref As AcadExternalReference
   Dim strValue As String
   Dim intValue As Integer
   
   On Error Resume Next
   
   'проверяем существование указанного файла
   If Dir(strDwgFileFullPath) = "" Then
      AddBlocksFromDWG = False
      Exit Function
   End If
   'проверка имени текущего чертежа и вставляемого
   If ThisDrawing.FullName <> strDwgFileFullPath Then
      'вставляем ссылку
      Set objXref = ThisDrawing.ModelSpace.AttachExternalReference(strDwgFileFullPath, "Name_", dPt, 1, 1, 1, 0, False)
      ThisDrawing.Blocks.Item(objXref.Name).Bind True
      objXref.Delete
      ThisDrawing.Blocks.Item("Name_").Delete
   End If
   
   AddBlocksFromDWG = True
   
End Function

Public Function GetLayerDBX(strLayerName As String, oDoc As AxDbDocument) As AcadLayer
   'возвращает объект слоя, с заданным именем
   'если слоя с таким именем не было, он создается
   
   On Error GoTo HasError
   Set GetLayerDBX = oDoc.Layers.Item(strLayerName)
   GetLayerDBX.Lock = False
   GetLayerDBX.LayerOn = True
   If Not GetLayerDBX Is oDoc.ActiveLayer Then
      GetLayerDBX.Freeze = False
   End If

Exit Function

HasError:
   Set GetLayerDBX = oDoc.Layers.Add(strLayerName)
   
End Function

Public Function GetLayer(strLayerName As String) As AcadLayer
   'возвращает объект слоя, с заданным именем
   'если слоя с таким именем не было, он создается
   
   On Error GoTo HasError
   Set GetLayer = ThisDrawing.Layers.Item(strLayerName)
   GetLayer.Lock = False
   GetLayer.LayerOn = True
   If Not GetLayer Is ThisDrawing.ActiveLayer Then
      GetLayer.Freeze = False
   End If

Exit Function

HasError:
   Set GetLayer = ThisDrawing.Layers.Add(strLayerName)
   
End Function



Public Function MakeTableStyleForSpec() As String
   'создание табличного стиля для спецификаций
   'для масштаба 1:1, в конкретных условиях нужно отмасштабировать после заполнения
   
   Dim objTableStyle As AcadTableStyle
   Dim objTextStyle As AcadTextStyle
   Dim objDictTableStyle As AcadDictionary
   Dim strTableStyleName As String
   Dim strTextStyleName As String
   
   'создаем табличный стиль в словаре чертежа
   Set objDictTableStyle = ThisDrawing.Dictionaries.Item("ACAD_TABLESTYLE")
   strTableStyleName = "Спецификация"
   On Error Resume Next 'не хорошо конечно, надо сделать проверки
   Set objTableStyle = objDictTableStyle.AddObject(strTableStyleName, "AcDbTableStyle")
   
   'создаем текстовый стиль для таблиц
   strTextStyleName = "Спецификаций"
   Set objTextStyle = ThisDrawing.TextStyles.Add(strTextStyleName)
   On Error GoTo 0
   
   'задаем шрифт, у нас принят ариал
   objTextStyle.SetFont "Arial", False, False, 0, 34 'значения получил по GetFont для нужного стиля
   
   'настраиваем таблицу
   'задаем текстовый стиль всем типам ячеек
   objTableStyle.SetTextStyle AcRowType.acDataRow + AcRowType.acHeaderRow _
                           + AcRowType.acTitleRow + AcRowType.acUnknownRow, strTextStyleName
   'задаем высоту текста
   objTableStyle.SetTextHeight AcRowType.acDataRow + AcRowType.acUnknownRow, 2.5
   objTableStyle.SetTextHeight AcRowType.acHeaderRow + AcRowType.acTitleRow, 3
   'задаем выравниваниев ячейках
   objTableStyle.SetAlignment AcRowType.acHeaderRow + AcRowType.acTitleRow, acMiddleCenter
   objTableStyle.SetAlignment AcRowType.acDataRow + AcRowType.acUnknownRow, acMiddleLeft
   'задаем отступы в ячейках
   objTableStyle.HorzCellMargin = 1.5
   objTableStyle.VertCellMargin = 1
   'задаем толщины границ
   objTableStyle.SetGridLineWeight AcGridLineType.acHorzBottom + AcGridLineType.acHorzInside + AcGridLineType.acHorzTop _
                + AcGridLineType.acVertInside + AcGridLineType.acVertLeft + AcGridLineType.acVertRight, _
                AcRowType.acTitleRow + AcRowType.acHeaderRow, AcLineWeight.acLnWt050
   objTableStyle.SetGridLineWeight AcGridLineType.acHorzBottom + AcGridLineType.acHorzTop + _
               AcGridLineType.acVertInside + AcGridLineType.acVertLeft + AcGridLineType.acVertRight, _
               AcRowType.acDataRow + AcRowType.acUnknownRow, AcLineWeight.acLnWt050
   objTableStyle.SetGridLineWeight AcGridLineType.acHorzInside, _
               AcRowType.acDataRow + AcRowType.acUnknownRow, AcLineWeight.acLnWt025
   'задаем цвет тексту
   Dim color As New AcadAcCmColor
   color.SetRGB 255, 0, 0
   objTableStyle.SetColor AcRowType.acDataRow + AcRowType.acHeaderRow _
                        + AcRowType.acTitleRow + AcRowType.acUnknownRow, color
   
   'вроде все, посмотрим
   
   'возвращаем имя созданного стиля
   MakeTableStyleForSpec = strTableStyleName
   
End Function


'Public Function GetSelSet(strSelName As String) As AcadSelectionSet
'   'возвращает набор, с заданным именем
'   'если набор с таким именем был, он очищается
'
'   On Error GoTo HasError
'   Set GetSelSet = ThisDrawing.SelectionSets.item(strSelName)
'   GetSelSet.Clear
'
'Exit Function
'
'HasError:
'   Set GetSelSet = ThisDrawing.SelectionSets.add(strSelName)
'
'End Function

Public Function SortyrBlInCol(colBl As Collection)
   'сортировка блоков в коллекции, по имени
   
   Dim objBlRefTemp As AcadBlockReference
   Dim i As Integer
   Dim j As Integer
   Dim intCount As Integer
   
   intCount = colBl.Count
   
   For i = 1 To intCount - 1
      For j = 1 To intCount - i
         If StrComp(colBl.Item(j).Name, colBl.Item(j + 1).Name, vbTextCompare) = 1 Then
            Set objBlRefTemp = colBl.Item(j)
            colBl.Remove j
            colBl.Add objBlRefTemp, , , j
         End If
      Next
   Next
   
End Function

Attribute VB_Name = "Module1"
Option Explicit

   Enum eType
      KD = 0
      KO = 1
      K = 2
   End Enum
   
   Public colOtherBl As New Collection
   Public colBlNotConstr As New Collection
   Public colBlNotMassa As New Collection
   
   Public colZerkalBl As New Collection

Public Sub AddAttKarkasaInBiblBlocks()
   'добавление атрибутов в файлы блоков в библиотеке
   
   'указываем папку библиотеки
   'перебираем вложенные папки, 1 уровня вложения
   'перебираем файлы dwg в каждой вложенной папке, это схемы блоков каркасов
   'ищем атрибуты, и проверяем: 1 д.б. на слое Att~Marka, второй масса, третий конструкция=ростверк
   
   Dim objAttMarka As AcadAttribute
   Dim objAtt As AcadAttribute
   Dim objEntity As AcadEntity
   Dim objLayer As AcadLayer
   Dim vPtMaterial As Variant
   Dim dPtMaterial(2) As Double
   Dim strName As String
   
   Dim docOpen As AXDBLib.AxDbDocument
   Dim docMS As AcadModelSpace
   Dim docLayers As AcadLayers
   
   Dim sFolder As String
   Dim sBiblPath As String
   Dim sFileOpen As String
   
   Dim bolAttrMarka As Boolean
   Dim bolAttrMassa As Boolean
   Dim bolAttrConstr As Boolean
   Dim bolAttrKolShtuk As Boolean
   
   Dim asErrorFile() As String
   Dim intCountErrorFilea As Integer
   
   Dim asErrorEntity() As String
   Dim intCountErrorEntity As Integer
   
   Dim asErrorAtt() As String
   Dim intCountErrorAtt As Integer
   
   Dim asErrorAttMarka() As String
   Dim intCountErrorAttMarka As Integer
   
   Dim dPt1(2) As Double
   Dim dPt2(2) As Double
   
   Dim intLen As Integer
   Dim asFolders() As String
   Dim intCountFolders As Integer
   Dim i As Integer
   
   sBiblPath = "\\Sgpsrv2\СПД\Конструкторы\Елена\Библиотека 5\"
   
   Dim oSysFile As New Scripting.FileSystemObject
   Dim oFolder As Folder
   Dim oSubFolder As Folder
   Dim oFile As File
   Set oFolder = oSysFile.GetFolder(sBiblPath)
   
   
For Each oSubFolder In oFolder.SubFolders
   For Each oFile In oSubFolder.Files
    If Not oFile.Type = "Чертеж AutoCAD" Then GoTo NextFile
         Dim oKar As New clKarkas
         
         sFileOpen = Left(oFile.Name, Len(oFile.Name) - 4)
         oKar.Name = sFileOpen

         If oKar.Error <> "" Then
            ReDim Preserve asErrorFile(intCountErrorFilea)
            asErrorFile(intCountErrorFilea) = oFile.Path
            intCountErrorFilea = intCountErrorFilea + 1
            GoTo NextFile
         End If
         
         Set docOpen = New AXDBLib.AxDbDocument
         docOpen.Open sBiblPath & oSubFolder.Name & "\" & sFileOpen & ".dwg"
         Set docMS = docOpen.ModelSpace
         Set docLayers = docOpen.Layers
         
         bolAttrMarka = False
         For Each objEntity In docMS
            If TypeOf objEntity Is AcadAttribute Then
               Set objAtt = objEntity
               Select Case objAtt.Layer
                  Case "Att~Massa"
                     objAtt.TextString = ""
                  Case "Att~Marka"
                     If bolAttrMarka = True Then
                        objAtt.Delete
                     End If
                     Set objAttMarka = objAtt
                     'Tag должен быть = имени блока
                     If StrComp(objAtt.TagString, sFileOpen, vbTextCompare) <> 0 Then
                        objAtt.TagString = sFileOpen
                     End If
                     'Promt д.б. = "МАРКА"
                     objAtt.PromptString = "МАРКА"
                     objAtt.TextString = oKar.strFirstName
                     bolAttrMarka = True
                  Case Else
                     objAtt.Delete
               End Select
            ElseIf Not TypeOf objEntity Is AcadLine Then
               'не понятный примитив
               ReDim Preserve asErrorEntity(intCountErrorEntity)
               asErrorEntity(intCountErrorEntity) = objEntity.ObjectName
               intCountErrorEntity = intCountErrorEntity + 1

               objEntity.Delete
            End If
         Next
         'проверяем все ли атрибуты на месте
         If bolAttrMarka = False Then
            'недолжно быть такого
            ReDim Preserve asErrorAttMarka(intCountErrorAttMarka)
'            asErrorAttMarka(intCountErrorAttMarka) = asFolders(i) & "\" & sFileOpen
            asErrorAttMarka(intCountErrorAttMarka) = oFile.Path
            intCountErrorEntity = intCountErrorEntity + 1
            GoTo NextFile
         End If

         'создаем атрибуты
         intLen = 0
         If oKar.intKolShtuk > 1 Then
            'создаем атрибут кол.штук
            Set objAtt = objAttMarka.Copy
            objAtt.Layer = LibFunctions.GetLayerDBX("Каркасы", docOpen).Name
            intLen = 300
            dPt2(0) = objAttMarka.InsertionPoint(0): dPt2(1) = objAttMarka.InsertionPoint(1) - intLen
            objAtt.Move objAttMarka.InsertionPoint, dPt2
            objAtt.PromptString = "кол."
            objAtt.TextString = "шт." & oKar.intKolShtuk
         End If
         'создаем атрибут массы
         Set objAtt = objAttMarka.Copy
         objAtt.Layer = LibFunctions.GetLayerDBX("Att~Massa", docOpen).Name
         intLen = intLen + 300
         dPt2(0) = objAttMarka.InsertionPoint(0): dPt2(1) = objAttMarka.InsertionPoint(1) - intLen
         objAtt.Move objAttMarka.InsertionPoint, dPt2
         objAtt.Invisible = True
         objAtt.PromptString = "МАССА"
         objAtt.TextString = ""
         'создаем атрибут конструкции
         Set objAtt = objAttMarka.Copy
         objAtt.Layer = LibFunctions.GetLayerDBX("Att~Constr", docOpen).Name
         intLen = intLen + 300
         dPt2(0) = objAttMarka.InsertionPoint(0): dPt2(1) = objAttMarka.InsertionPoint(1) - intLen
         objAtt.Move objAttMarka.InsertionPoint, dPt2
         objAtt.Invisible = True
         objAtt.PromptString = "КОНСТРУКЦИЯ"
         objAtt.TextString = "Ростверк"

      If Not docOpen Is Nothing Then
         docOpen.SaveAs docOpen.Name
      End If
NextFile:
   Next 'file
Next 'subfolder
   
   MsgBox "intCountErrorAttMarka = " & intCountErrorAttMarka & vbCr & _
         "intCountErrorEntity = " & intCountErrorEntity & vbCr & _
         "intCountErrorFilea = " & intCountErrorFilea

End Sub

Public Sub AddAttKarkasaInDrawing()
   'добавление атрибута Конструкция=Ростверк во все блоки каркаса в текущем чертеже ростверка
   
   Dim oBl As AcadBlock
   Dim oBlRef As AcadBlockReference
   Dim oEnt As AcadEntity
   Dim oAtt As AcadAttribute
   Dim oAttMarka As AcadAttribute
   Dim dPt2(2) As Double
   Dim bolAtrMassa As Boolean
   
   For Each oBl In ThisDrawing.Blocks
      If InStr(oBl.Name, "К") <> 0 Then
         For Each oEnt In oBl
            bolAtrMassa = False
            If TypeOf oEnt Is AcadAttribute Then
               Set oAtt = oEnt
               Select Case LCase(oAtt.PromptString)
                  Case "марка"
                     Set oAttMarka = oAtt
                     dPt2(0) = oAtt.InsertionPoint(0): dPt2(1) = oAtt.InsertionPoint(1)
                  Case "масса"
                     bolAtrMassa = True
                  Case "конструкция"
                     GoTo NextBl
               End Select
               If dPt2(1) > oAtt.InsertionPoint(1) Then
                  dPt2(1) = oAtt.InsertionPoint(1)
               End If
            End If
         Next 'oEnt In oBl
         dPt2(1) = oAttMarka.InsertionPoint(1) - 300
         If bolAtrMassa = False Then
            'создаем атрибут массы
            Set oAtt = oAttMarka.Copy
            oAtt.Layer = LibFunctions.GetLayer("Att~Massa").Name
            oAtt.Move oAttMarka.InsertionPoint, dPt2
            oAtt.Invisible = True
            oAtt.PromptString = "МАССА"
            oAtt.TextString = ""
            dPt2(1) = dPt2(1) - 300
         End If
         'создаем атрибут конструкции
         Set oAtt = oAttMarka.Copy
         oAtt.Layer = LibFunctions.GetLayer("Att~Constr").Name
         oAtt.Move oAttMarka.InsertionPoint, dPt2
         oAtt.Invisible = True
         oAtt.PromptString = "КОНСТРУКЦИЯ"
         oAtt.TextString = "Ростверк"
      End If 'InStr(oBl.Name, "К") <> 0 Then
      
NextBl:
   Next 'oBl In ThisDrawing.Blocks
   
'
'   ThisDrawing.SendCommand "_AttSync" & vbCr & "Имя" & vbCr & "*" & vbCr
   
   'заменить все блоки каркасов
   Dim oBlInsert As AcadBlockReference
   Dim oBlZerkal As AcadBlockReference
   Dim oAttInsert As AcadAttributeReference
   Dim oAttRef As AcadAttributeReference
   Dim selSet As AcadSelectionSet
   Dim intCode(1) As Integer
   Dim varDate(1) As Variant
   Dim varAtr As Variant
   
   intCode(0) = 0: varDate(0) = "insert"
   intCode(1) = 66: varDate(1) = 1
   Set selSet = LibFunctions.GetSelSet("Каркасы")
   selSet.Select acSelectionSetAll, , , intCode, varDate
   ThisDrawing.ActiveLayer = LibFunctions.GetLayer("Каркасы")
   For Each oBlRef In selSet
      If InStr(oBlRef.Name, "К") <> 0 Then
         'вставляем блок
         Set oBlInsert = ThisDrawing.ModelSpace.InsertBlock(oBlRef.InsertionPoint, oBlRef.Name, _
            1, 1, 1, oBlRef.Rotation)
         If oBlRef.XScaleFactor < 1 Then
            'зеркалим по х
            dPt2(0) = oBlInsert.InsertionPoint(0): dPt2(1) = oBlInsert.InsertionPoint(1) + 100
            Set oBlZerkal = oBlInsert.Mirror(oBlInsert.InsertionPoint, dPt2)
            oBlInsert.Delete
            Set oBlInsert = oBlZerkal
         End If
         If oBlRef.YScaleFactor < 1 Then
            'зеркалим по y
            dPt2(0) = oBlInsert.InsertionPoint(0) + 100: dPt2(1) = oBlInsert.InsertionPoint(1)
            Set oBlZerkal = oBlInsert.Mirror(oBlInsert.InsertionPoint, dPt2)
            oBlInsert.Delete
            Set oBlInsert = oBlZerkal
         End If
         For Each varAtr In oBlRef.GetAttributes
            Set oAttRef = varAtr
            If oAttRef.Layer = "Att~Marka" Then
               Exit For
            End If
         Next
         For Each varAtr In oBlInsert.GetAttributes
            Set oAttInsert = varAtr
            If oAttInsert.Layer = "Att~Marka" Then
               oAttInsert.Rotation = oAttRef.Rotation
               oAttInsert.TextAlignmentPoint = oAttRef.TextAlignmentPoint
            End If
         Next
         oBlRef.Delete
      End If
     
   Next
End Sub

Public Sub ViewBadKarkasy()
   'проверка вхождений блоков каркасов
   'вывод списка неправильных:
   'без атрибута Конструкция=Ростверк
   'без атрибута массы
   
   Dim oBlRef As AcadBlockReference
   Dim selSet As AcadSelectionSet
   Dim intCode(1) As Integer
   Dim varDate(1) As Variant
   Dim varAtr As Variant
   Dim bolAttConstr As Boolean
   Dim bolAttMassa As Boolean
   Dim bolBadKar As Boolean
   Dim oAtt As AcadAttributeReference
   
   intCode(0) = 0: varDate(0) = "insert"
   intCode(1) = 66: varDate(1) = 1
   Set selSet = LibFunctions.GetSelSet("Каркасы")
   selSet.Select acSelectionSetAll, , , intCode, varDate
   
   Call LibFunctions.GetLayer("Att~Constr")
   
   For Each oBlRef In selSet
      bolAttConstr = False 'входное значение
      bolAttMassa = False
      If InStr(oBlRef.Name, "К") <> 0 Then
         For Each varAtr In oBlRef.GetAttributes
            If LCase(varAtr.TextString) = "ростверк" Then
               bolAttConstr = True
               varAtr.Layer = "Att~Constr"
            End If
            If varAtr.Layer = "Att~Massa" Then
               bolAttMassa = True
            End If
         Next
         If bolAttConstr = False Then
            'нет атрибута Конструкции
            colBlNotConstr.Add oBlRef
            bolBadKar = True
         End If
         If bolAttMassa = False Then
            'нет атрибута Массы
            colBlNotMassa.Add oBlRef
            bolBadKar = True
         End If
      Else
         'заносим в набор блоки без буквы К
         colOtherBl.Add oBlRef
      End If
   Next
   
   If bolBadKar = True Then
      FormaProverky.Show vbModeless
   End If
   
End Sub



Public Sub ProvMassy()
   'проверка массы каркаса
   
   Dim oKar As clKarkas
   Dim oBlRef As AcadObject
   Dim vPt As Variant
   Dim dMassaAtr As Double
   Dim dMassaTeor As Double
   Dim strText As String
   Dim sMassaAtr As String
   Dim varAtr As Variant
   Dim sKarName As String
   
Do
   ThisDrawing.Utility.GetEntity oBlRef, vPt
   Select Case oBlRef.ObjectName
      Case "AcDbBlockReference"
         'определяем массу по атрибуту массы
         For Each varAtr In oBlRef.GetAttributes
            If varAtr.Layer = "Att~Massa" Then
               dMassaAtr = Val(varAtr.TextString)
               sMassaAtr = varAtr.TextString
               sKarName = oBlRef.Name
               Exit For
            End If
         Next
      Case "AcDbAttributeDefinition"
         dMassaAtr = Val(oBlRef.TextString)
         sMassaAtr = oBlRef.TextString
         sKarName = oBlRef.TagString
      Case Else
         MsgBox "Неопределен тип примитива!"
   End Select
   If dMassaAtr <> 0 Then
      Set oKar = New clKarkas
      oKar.Name = sKarName
      If oKar.Error = "" Then
         oKar.Massa
         If oKar.bolП = True Then
            dMassaTeor = oKar.dMassaProsKar
         Else
            dMassaTeor = oKar.dMassaPlosKar
         End If
         If dMassaTeor = 0 Then
            MsgBox "Теор.масса не определена"
         End If
      Else
         MsgBox "Ошибка при опр. хар-ик по имени каркаса" & vbCr & _
               oKar.Error
      End If
   Else
      MsgBox "Масса по атрибуту не определена"
   End If
   If dMassaAtr > dMassaTeor Then
      strText = "По атр. больше"
   ElseIf dMassaAtr = dMassaTeor Then
      strText = "Равны"
   Else
      strText = "Теор больше"
   End If
   MsgBox "По атрибуту(текст) = " & sMassaAtr & vbCr & _
         "Теор. = " & dMassaTeor & vbCr & _
         "Вывод: " & strText
Loop While MsgBox("Продолжить?", vbYesNo) = vbYes
   
End Sub

Public Sub VievZerkalKarkasy()
   'просмотр зеркальных каркасов
   
   Dim selSet As AcadSelectionSet
   Dim intCode(1) As Integer
   Dim varDate(1) As Variant
   
   Dim oBlRef As AcadBlockReference
   
   intCode(0) = 0: varDate(0) = "insert"
   intCode(1) = 66: varDate(1) = 1
   Set selSet = LibFunctions.GetSelSet("Каркасы")
   selSet.Select acSelectionSetAll, , , intCode, varDate
   
   
   Set colZerkalBl = New Collection
   For Each oBlRef In selSet
'      If InStr(oBlRef.Name, "К") Then
         If oBlRef.XEffectiveScaleFactor < 0 Or oBlRef.YEffectiveScaleFactor < 0 Then
            colZerkalBl.Add oBlRef
         End If
'      End If
   Next
   
   If colZerkalBl.Count > 0 Then
      FormaProverky.Show vbModeless
   End If
   
End Sub

Public Sub AddAtrKarToShema()
   'добавление атрибутов массы и конструкции в схеме блоков каркасов
   
   Dim selSet As AcadSelectionSet
   Dim intCode(1) As Integer
   Dim varDate(1) As Variant
   Dim dPt2(2) As Double
   
   Dim oAtt As AcadAttribute
   Dim oAttCopy As AcadAttribute
   
   intCode(0) = 0: varDate(0) = "ATTDEF"
   intCode(1) = 3: varDate(1) = "МАРКА"
   Set selSet = LibFunctions.GetSelSet("Каркасы")
   selSet.Select acSelectionSetAll, , , intCode, varDate
   
   Call LibFunctions.GetLayer("Att~Massa")
   Call LibFunctions.GetLayer("Att~Constr")
   
   For Each oAtt In selSet
      'создаем атрибут массы
      Set oAttCopy = oAtt.Copy
      oAttCopy.Layer = "Att~Massa"
      dPt2(0) = oAtt.InsertionPoint(0): dPt2(1) = oAtt.InsertionPoint(1) - 300
      oAttCopy.Move oAtt.InsertionPoint, dPt2
      oAttCopy.Invisible = True
      oAttCopy.PromptString = "МАССА"
      oAttCopy.TextString = ""
      
      'создаем атрибут конструкции
      Set oAttCopy = oAtt.Copy
      oAtt.Layer = "Att~Constr"
      dPt2(1) = dPt2(1) - 300
      oAtt.Move oAtt.InsertionPoint, dPt2
      oAtt.Invisible = True
      oAtt.PromptString = "КОНСТРУКЦИЯ"
      oAtt.TextString = "Ростверк"
   Next
   
End Sub

Public Sub SetMassaPusto()

   Dim selSet As AcadSelectionSet
   Dim intCode(1) As Integer
   Dim varDate(1) As Variant
   Dim dPt2(2) As Double
   Dim oAtt As AcadAttribute
   Dim oAttCopy As AcadAttribute
   
   'НА СХЕМАХ
   
   intCode(0) = 0: varDate(0) = "ATTDEF"
   intCode(1) = 3: varDate(1) = "МАССА"
   Set selSet = LibFunctions.GetSelSet("Каркасы")
   selSet.Select acSelectionSetAll, , , intCode, varDate
   
   For Each oAtt In selSet
      oAtt.TextString = ""
   Next
   
   'на чертеже
   
End Sub


Public Sub IsprVerBiblBlocks()
   'исправление версии файлов с 21 на 18 (2004)
   
   Dim sFileOpen As String
   Dim sBiblPath As String
   Dim docOpen As AcadDocument
   Dim oSysFile As New Scripting.FileSystemObject
   Dim oFolder As Folder
   Dim oSubFolder As Folder
   Dim oFile As File
   
   sBiblPath = "D:\Вильдар\Ростверки\БИБЛИОТЕКА 4\"
   Set oFolder = oSysFile.GetFolder(sBiblPath)
   
For Each oSubFolder In oFolder.SubFolders
   For Each oFile In oSubFolder.Files
    If Not oFile.Type = "Чертеж AutoCAD" Then GoTo NextFile
         
         sFileOpen = Left(oFile.Name, Len(oFile.Name) - 4)
         
         Set docOpen = Documents.Open(sBiblPath & oSubFolder.Name & "\" & sFileOpen & ".dwg")

         docOpen.SaveAs docOpen.Name, ac2004_dwg
         docOpen.Close
NextFile:
   Next 'file
Next 'subfolder

End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True

Public Sub Teer()
   
   Dim selSet As AcadSelectionSet
   Dim intCode(1) As Integer
   Dim varDate(1) As Variant
   Dim oBlRef As AcadBlockReference
   Dim objBlockRef2 As AcadBlockReference
   Dim vPt As Variant
   Dim vMin As Variant
   Dim vMax As Variant
   Dim vMin1 As Variant
   Dim vMax1 As Variant
   Dim vMin2 As Variant
   Dim vMax2 As Variant
   
   ThisDrawing.Utility.GetEntity oBlRef, vPt
   
   oBlRef.GetBoundingBox vMin, vMax
   vMin1 = vMin
   vMax1 = vMax
   vMin1(0) = vMin(0) - 200: vMin1(1) = vMin(1) - 200
   vMax1(0) = vMax(0) + 200: vMax1(1) = vMax(1) + 200
   
   Set selSet = LibFunctions.GetSelSet("Вокруг блока")
   
   intCode(0) = 0: varDate(0) = "insert"
   intCode(1) = 2: varDate(1) = oBlRef.Name
   
   selSet.Select acSelectionSetCrossing, vMin, vMax, intCode, varDate
   
   If selSet.Count <> 2 Then
      MsgBox "Не 2"
   End If
   
   For Each objBlockRef2 In selSet 'перебор всех объектов набора
   
      If Not objBlockRef2 Is oBlRef Then
         'проверка наложения по границе
         'сравнение точек BoundingBox'оф
         'получаем границы блока
         objBlockRef2.GetBoundingBox vMinPt2, vMaxPt2
         If ProvBoundingBox(vMin, vMinPt2, vMax, vMaxPt2, 200) = True Then
            'заносим блок в колекцию (потенциально) наложенных блоков
            MsgBox "Наложение"
         End If
      End If 'Id1 <> Id2 Then
   Next 'lCounter = 1 To objSelSet.Count 'пере
   
End Sub

Private Function ProvBoundingBox(MinPt1 As Variant, MinPt2 As Variant, MaxPt1 As Variant, MaxPt2 As Variant, Dopusk As Integer) As Boolean
   'проверка наложенитя точек
   'наложение считается совпадение (в допусках) обоих точек BoundingBox
   'True - наложение
   
   'проверяем первую точку
   If MinPt2(0) < MinPt1(0) + Dopusk And MinPt2(0) > MinPt1(0) - Dopusk And _
       MinPt2(1) < MinPt1(1) + Dopusk And MinPt2(1) > MinPt1(1) - Dopusk Then
       'проверяем вторую точку
      If MaxPt2(0) < MaxPt1(0) + Dopusk And MaxPt2(0) > MaxPt1(0) - Dopusk And _
          MaxPt2(1) < MaxPt1(1) + Dopusk And MaxPt2(1) > MaxPt1(1) - Dopusk Then
          'значит точки лежат в пределах наложения, т.е. блоки накладываются
          ProvBoundingBox = True
      Else
         ProvBoundingBox = False
      End If
   Else
      ProvBoundingBox = False
   End If
   
End Function

Attribute VB_Name = "clKarkas"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'параметры каркаса, определяемые по имени

   Dim strName As String
   Public strFirstName As String 'имя до (шт.2)
   Public bolП As Boolean
   Dim intLenRab As Integer
   Dim strError As String
   
   Dim intDiamVerh As Integer
   Dim intDiamNiz As Integer
   Dim intDiamPop As Integer
   Dim intHvostLeft As Integer
   Dim intHvostRight As Integer
   Public intN As Integer
   Public bolD As Boolean
   Public strType As String 'КО, КД, К
   Public intKolShtuk As Integer 'кол штук (шт.2)
   
   Public intDiamVerhSvysSter As Integer
   Public intDiamNizSvysSter As Integer
   Public intLenSvyzSter As Integer
   Public intShagVerhSvyzSter As Integer 'шаг связевых стержней, верхних
   Public intShagNizSvyzSter As Integer 'шаг связевых стержней нижних
   Public intLenPopSter As Integer 'для высоты роств. 400, =400-(40+80)+50
   
   Public dMassaPlosKar As Double
   Public dMassaProsKar As Double
   
      
Public Property Get Name() As String
   Name = strName
End Property
Public Property Let Name(ByVal vNewValue As String)
   
   Dim intValue As Integer
   Dim strValue As String
   Dim strValue2 As String
   Dim strNameVal As String
   Dim intType As Integer
   
   strError = ""
   strName = ""
   bolП = False
   intLenRab = 0
   strFirstName = ""
   intDiamVerh = 0
   intDiamNiz = 0
   intDiamPop = 0
   intHvostLeft = 0
   intHvostRight = 0
   intN = 0
   bolD = False
   strType = ""
   intKolShtuk = 0
   
   strName = vNewValue
   
   intValue = InStr(strName, "-")
   'оставшаяся строка до "-"
   If intValue <> 0 Then
      'переводим все что после "-" в нижний регистр
      strValue = LCase(Mid(strName, intValue + 1))
      strValue2 = Left(strName, intValue)
      strName = strValue2 & strValue
      strNameVal = Left(strName, intValue - 1)
   Else
      strNameVal = strName
   End If
   'если есть скобки то отбрасываем их пока
   intValue = InStr(strNameVal, "(")
   If intValue <> 0 Then
      strNameVal = Left(strNameVal, intValue - 1)
   End If
   
   'по полученному имени определяем тип каркаса и все остальное
   
   'пространственный каркас, Да/Нет
   intValue = InStr(LCase(strNameVal), "п")
   If intValue = 0 Then
      bolП = False
   Else
      bolП = True
   End If
   
   strNameVal = Right(strNameVal, Len(strNameVal) - intValue)
   
   'определяем раб длину L= n*150
   intN = Val(strNameVal)
   intLenRab = intN * 150
   If intLenRab = 0 Then
      strError = "Рабочая длина каркаса (n*150) - не определена. "
      Exit Property
   End If
   
   intValue = InStr(LCase(strNameVal), "к")
   'оставшаяся строка после "к"
   strNameVal = Right(strNameVal, Len(strNameVal) - intValue)
   
   'после "к" может стоять или "О","Д", или ничего
   strValue = LCase(Mid(strNameVal, 1, 1))
   
   If strValue = "о" Then
      intType = eType.KO
      strType = "КО"
      strValue = Right(strNameVal, Len(strNameVal) - 1)
      If Len(strValue) > 1 Then
         strError = "После КО может быть максимум одна цифра. "
         Exit Property
      End If
   ElseIf strValue = "д" Then
      intType = eType.KD
      strType = "КД"
      strValue = Right(strNameVal, Len(strNameVal) - 1)
      If Len(strValue) > 2 Then
         strError = "После КД может быть максимум две цифры. "
         Exit Property
      End If
   ElseIf strValue = "" Then
      intType = eType.K
      strType = "К"
   Else
      strError = "После К стоит недопустимый символ. "
   End If
   'определяем длину хвостов
   Select Case intType
      Case eType.KD
         intHvostLeft = ReturnLenHvosta(Val(Left(strValue, 1)))
         intHvostRight = ReturnLenHvosta(Val(Right(strValue, 1)))
      Case eType.KO
         intHvostLeft = 20
         intHvostRight = ReturnLenHvosta(Val(Left(strValue, 1)))
      Case eType.K
         intHvostLeft = 20
         intHvostRight = 20
   End Select
   
   If intHvostLeft = 0 Or intHvostRight = 0 Then
      strError = "Длина хвостов не определена. "
   End If
   
   'проверяем то что после "-"
   
   intValue = InStr(strName, "-")
   'оставшаяся строка после "-"
   strNameVal = Right(strName, Len(strName) - intValue)
   'если есть скобки то отбрасываем их пока
   intValue = InStr(strNameVal, "(")
   If intValue <> 0 Then
      strNameVal = Left(strNameVal, intValue - 1)
   End If
   
   If InStr(strNameVal, "д") <> 0 Then
      bolD = True
      intLenRab = intLenRab + 100
   End If
   
   intValue = InStr(strNameVal, "в")
   If intValue = 0 Then
      intDiamVerh = 12
   Else
      'после "в" может быть "н", или цифра
      If Mid(strNameVal, intValue + 1, 1) Like "[1-9]" Then
         'если цифра
         intDiamVerh = ReturnDiamStandard(Val(Right(strNameVal, Len(strNameVal) - intValue)))
      Else
         'если не цифра
         intDiamVerh = ReturnDiamStandard(Val(Right(strNameVal, Len(strNameVal) - (intValue + 1))))
      End If
      If intDiamVerh = 0 Then
         strError = "Диаметр верхней арматуры не определен. "
         Exit Property
      End If
   End If
   intValue = InStr(strNameVal, "н")
   If intValue = 0 Then
      intDiamNiz = 10
   Else
      'после "н" может быть только цифра
      If Mid(strNameVal, intValue + 1, 1) Like "[1-9]" Then
         intDiamNiz = ReturnDiamStandard(Val(Right(strNameVal, Len(strNameVal) - intValue)))
      End If
      If intDiamNiz = 0 Then
         strError = "Диаметр нижней арматуры не определен. "
         Exit Property
      End If
   End If
   
   intValue = InStr(strNameVal, "п")
   If intValue = 0 Then
      intDiamPop = 8
   Else
      'после "н" может быть только цифра
      If Mid(strNameVal, intValue + 1, 1) Like "[1-9]" Then
         intDiamPop = ReturnDiamStandard(Val(Right(strNameVal, Len(strNameVal) - intValue)))
      End If
      If intDiamPop = 0 Then
         strError = "Диаметр поперечной арматуры не определен. "
         Exit Property
      End If
   End If
   
   'проверяем если есть скобки
   intValue = InStr(LCase(strName), "(шт.")
   If intValue <> 0 Then
'      If InStr(LCase(strName), "(шт.") = 0 Then
'         strError = "Неопределено то что в скобках! " & vbCrLf & _
'                  "Кол-во плоских каркасов записывается так: (шт.2) "
'         Exit Property
'      Else
         'определяем кол-во
         intKolShtuk = Val(Mid(strName, intValue + 4))
         If intKolShtuk = 0 Then
            strError = "Неопределено кол-во каркасов! " & vbCrLf & _
                  "Кол-во плоских каркасов записывается так: (шт.2) "
            Exit Property
'         End If
      End If
      If intKolShtuk <> 0 And bolП = True Then
         strError = "В пространственном каркасе не может быть установлено кол-во (шт." & intKolShtuk & ")! "
         Exit Property
      End If
   End If
   'имя каркаса без (шт.2)
   If intValue = 0 Then
      strFirstName = strName
   Else
      strFirstName = Left(strName, intValue - 1)
   End If
   
   If intKolShtuk = 0 Then intKolShtuk = 1
   
End Property

'Пространственный каркас, ДА/Нет
Public Property Get П() As Boolean
   П = bolП
End Property

'Раб длина L=n*150
Public Property Get LenRab() As Integer
   LenRab = intLenRab
End Property

'ошибка при обработке имени каркаса
Public Property Get Error() As String
   Error = strError
End Property


Private Function ReturnLenHvosta(Nomer As Integer) As Integer
   
   Select Case Nomer
      Case 0
         ReturnLenHvosta = 600
      Case 1
         ReturnLenHvosta = 400
      Case 2
         ReturnLenHvosta = 450
      Case 3
         ReturnLenHvosta = 500
      Case 4
         ReturnLenHvosta = 550
      Case 5
         ReturnLenHvosta = 700
      Case 6
         ReturnLenHvosta = 800
      Case 7
         ReturnLenHvosta = 900
   End Select
   
End Function

Private Function ReturnDiamStandard(Diam As Integer) As Integer
   'проверка соответствия входного диаметра списку стандартных диаметров арматуры
      
   Select Case Diam
      Case 8
         ReturnDiamStandard = Diam
      Case 10
         ReturnDiamStandard = Diam
      Case 12
         ReturnDiamStandard = Diam
      Case 14
         ReturnDiamStandard = Diam
      Case 16
         ReturnDiamStandard = Diam
      Case 18
         ReturnDiamStandard = Diam
      Case 20
         ReturnDiamStandard = Diam
      Case 22
         ReturnDiamStandard = Diam
      Case 25
         ReturnDiamStandard = Diam
      Case 28
         ReturnDiamStandard = Diam
      Case 32
         ReturnDiamStandard = Diam
      Case 36
         ReturnDiamStandard = Diam
      Case 40
         ReturnDiamStandard = Diam
      Case Else
         ReturnDiamStandard = 0
   End Select
   
End Function

Public Sub Massa()
   'определение массы каркаса
   
   Dim intKolPopSter As Integer
   Dim intKolVerhSvyzSter As Integer
   Dim intKolNizSvyzSter As Integer
'   Dim intLenSvyzSter As Integer
   
   If strName = "" Or strError <> "" Then Exit Sub
   
   'определяем массу плоского каркаса
   If intLenPopSter = 0 Then
      intLenPopSter = 330
   End If
   'определяем кол-во поперечных стержней
   If bolD = True Then
      intKolPopSter = intN + 2
   Else
      intKolPopSter = intN + 1
   End If
   
   'масса плоского каркаса
   dMassaPlosKar = ((MassaArm(intDiamNiz) + MassaArm(intDiamVerh)) * (intLenRab + intHvostLeft + intHvostRight) + _
               MassaArm(intDiamPop) * intLenPopSter * intKolPopSter) / 1000
   
   'считаем массу пространственного каркаса
   If bolП = True Then
      If intLenSvyzSter = 0 Then
         intLenSvyzSter = Val(strFirstName) * 100 + 100 - 20
      End If
      If intShagVerhSvyzSter = 0 Then
         intShagVerhSvyzSter = 300
      End If
      If intShagNizSvyzSter = 0 Then
         intShagNizSvyzSter = 300
      End If
      If intDiamVerhSvysSter = 0 Then
        intDiamVerhSvysSter = 8
      End If
      If intDiamNizSvysSter = 0 Then
         intDiamNizSvysSter = 8
      End If
      
      'определяем кол-во связевых стержней
      intKolVerhSvyzSter = intLenRab \ intShagVerhSvyzSter + 1
      If intLenRab Mod intShagVerhSvyzSter > 25 Then
         intKolVerhSvyzSter = intKolVerhSvyzSter + 1
      End If
      intKolNizSvyzSter = intLenRab \ intShagNizSvyzSter + 1
      If intLenRab Mod intShagNizSvyzSter > 25 Then
         intKolNizSvyzSter = intKolNizSvyzSter + 1
      End If
      
      dMassaProsKar = dMassaPlosKar * Val(strFirstName) + _
         ((MassaArm(intDiamVerhSvysSter) + MassaArm(intDiamNizSvysSter)) * _
         intLenSvyzSter * (intKolVerhSvyzSter + intKolNizSvyzSter)) / 1000
   End If
   
End Sub

Public Function MassaArm(intDiam As Integer) As Single
'проверка полученного диаметра арматуры - есть ли такой диаметр в списке диаметров
      
   Select Case intDiam
'      Case 6' пока не будем использовать ?????
'         ProvDiamArm = 0.222
      Case 8
         MassaArm = 0.395
      Case 10
         MassaArm = 0.617
      Case 12
         MassaArm = 0.888
      Case 14
         MassaArm = 1.208
      Case 16
         MassaArm = 1.578
      Case 18
         MassaArm = 1.998
      Case 20
         MassaArm = 2.466
      Case 22
         MassaArm = 2.984
      Case 25
         MassaArm = 3.85
      Case 28
         MassaArm = 4.83
      Case 32
         MassaArm = 6.31
      Case 36
         MassaArm = 7.99
      Case 40
         MassaArm = 9.87
   End Select
   
End Function
