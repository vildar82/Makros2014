Attribute VB_Name = "FormSelect"
Attribute VB_Base = "0{BBA9DA6B-3475-409D-BDAE-10E4B9503ED3}{75742F4B-082E-4DBD-909D-A58A627861F5}"
Attribute VB_GlobalNameSpace = False
Attribute VB_Creatable = False
Attribute VB_PredeclaredId = True
Attribute VB_Exposed = False
Attribute VB_TemplateDerived = False
Attribute VB_Customizable = False
Option Explicit
   
   Dim intFT(4) As Integer
   Dim varFD(4) As Variant
   
Private Sub cmbAll_Click()
   hide
   selSetCM.Select acSelectionSetAll, , , intFT, varFD
End Sub

Private Sub cmbSelect_Click()
   'выфбор на чертеже
   
   hide
   selSetCM.SelectOnScreen intFT, varFD
   
End Sub

Private Sub UserForm_Activate()
   
   Set selSetCM = Functions.GetSelSet("ЦентрТяжести")
   
   'значения для фильтра блоков и 3D-тел
   intFT(0) = -4: varFD(0) = "<OR"
    intFT(1) = 0: varFD(1) = "INSERT"
    intFT(2) = 0: varFD(2) = "3DSOLID"
    intFT(3) = 0: varFD(3) = "POINT"
    intFT(4) = -4: varFD(4) = "OR>"
   
End Sub

Attribute VB_Name = "Functions"
Option Explicit

Public Function GetLayer(strLayerName As String) As AcadLayer
   'возвращает объект слоя, с заданным именем
   'если слоя с таким именем не было, он создается
   
   On Error GoTo HasError
   Set GetLayer = ThisDrawing.Layers.Item(strLayerName)

Exit Function

HasError:
   Set GetLayer = ThisDrawing.Layers.Add(strLayerName)
   
End Function

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Attribute VB_Name = "Main"
Option Explicit
   'вставка точки центра тяжести тела
   'в блок или в отдельное тело
   
   Public Const pcsCMLayer As String = "Центр тяжести"
   Public selSetCM As AcadSelectionSet
   
Public Sub Main()
   
   Dim colBlName As New Collection
   Dim objBl As AcadBlock
   Dim strBlName As Variant
   Dim objLayer As AcadLayer
   Dim objEntity As AcadEntity
   Dim objEntitys(0) As AcadEntity
   Dim obj3Dsolid As Acad3DSolid
   Dim ptCT As AcadPoint
   Dim intCountCT As Integer 'кол-во проставленных точек ЦТ
   
   'выбора тел или блоков, по одному или всех
   FormSelect.Show
      
   'создаем слой центра тяжести
   Set objLayer = Functions.GetLayer(pcsCMLayer)
   objLayer.color = acCyan
   objLayer.Lock = False
   objLayer.LayerOn = True
   If Not ThisDrawing.ActiveLayer Is objLayer Then
      objLayer.Freeze = False
   End If
   
   'тип отображения точек на чертеже, крестиком
   ThisDrawing.SetVariable "PDMODE", 3
   ThisDrawing.SetVariable "PDSIZE", 50
   
   'удаляем точки попавшие в набор
   Dim strVal As String
   For Each objEntity In selSetCM
      strVal = objEntity.ObjectName
      If TypeOf objEntity Is AcadPoint Then
         If objEntity.Layer = pcsCMLayer Then
            Set objEntitys(0) = objEntity
            selSetCM.RemoveItems objEntitys
            objEntity.Delete
         End If
      End If
   Next
   
   'перебираем все выбранные тела и блоки
   For Each objEntity In selSetCM
      If TypeOf objEntity Is Acad3DSolid Then
         Set obj3Dsolid = objEntity
         Set ptCT = ThisDrawing.ModelSpace.AddPoint(obj3Dsolid.Centroid)
         ptCT.Layer = pcsCMLayer
         intCountCT = intCountCT + 1
      ElseIf TypeOf objEntity Is AcadBlockReference Then
         'отбираем имена блоков
         On Error Resume Next
         colBlName.Add objEntity.Name, objEntity.Name
      End If
   Next
   
   'во всех определениях блоков удаляем точки
   For Each strBlName In colBlName
      Set objBl = ThisDrawing.Blocks.Item(strBlName)
      For Each objEntity In objBl
         If TypeOf objEntity Is AcadPoint Then
            If objEntity.Layer = pcsCMLayer Then
               objEntity.Delete
            End If
         End If
      Next
   Next
   
   'находим блоки в коллекции определений блоков, и добавляем к телам точки центра тяжести
   For Each strBlName In colBlName
      Set objBl = ThisDrawing.Blocks.Item(strBlName)
      For Each objEntity In objBl
         If TypeOf objEntity Is Acad3DSolid Then
            Set obj3Dsolid = objEntity
            Set ptCT = objBl.AddPoint(obj3Dsolid.Centroid)
            ptCT.Layer = pcsCMLayer
            intCountCT = intCountCT + 1
         End If
      Next
   Next
   
   ThisDrawing.Regen acActiveViewport
   
   MsgBox "Кол-во проставленны точек ц.тяжести 3D-тел = " & intCountCT
   
End Sub
