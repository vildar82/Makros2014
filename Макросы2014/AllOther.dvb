Attribute VB_Name = "FormFindAtr"
Attribute VB_Base = "0{FA6392BC-E59F-4305-9FE5-747831B8F64C}{DE3CEA4D-3CC8-4B7A-BB86-EC82D91E0AC1}"
Attribute VB_GlobalNameSpace = False
Attribute VB_Creatable = False
Attribute VB_PredeclaredId = True
Attribute VB_Exposed = False
Attribute VB_TemplateDerived = False
Attribute VB_Customizable = False

Option Explicit

Dim iNext As Integer
Dim selSet As AcadSelectionSet
Dim sngLeft As Single
Dim sngTop As Single

Private Sub ComboBox1_Change()
  
  If CommandButton1.Caption = "Найти далее" Then
    CommandButton1.Caption = "Найти"
  End If
  
End Sub

Private Sub ComboBox1_Enter()
  
  If CommandButton1.Caption = "Найти далее" Then
    sngLeft = Me.Left
    sngTop = Me.top
    Me.Hide
    Me.Show
  End If
  
End Sub

Private Sub ComboBox1_Exit(ByVal Cancel As MSForms.ReturnBoolean)
  
  If CommandButton1.Caption = "Найти далее" Then
    sngLeft = Me.Left
    sngTop = Me.top
    Me.Hide
    Me.Show vbModeless
    Me.Left = sngLeft
    Me.top = sngTop
  End If
  
End Sub

Private Sub ComboBox1_KeyPress(ByVal KeyAscii As MSForms.ReturnInteger)
  If KeyAscii = 32 Then
    MsgBox "Пробелы нельзя вводить"
    KeyAscii = 0
  End If
End Sub


Private Sub CommandButton1_Click()
  
  Dim oAtrDef As AcadAttribute
  Dim iCode(1) As Integer
  Dim vData(1) As Variant
  Dim vMax As Variant
  Dim vMin As Variant
    
  If CommandButton1.Caption = "Найти" Then
    
    AddNameToCombo
    
    sngLeft = Me.Left
    sngTop = Me.top
    Me.Hide
    Me.Show vbModeless
    Me.Left = sngLeft
    Me.top = sngTop
  
    iCode(0) = 0: vData(0) = "ATTDEF"
    iCode(1) = 2: vData(1) = ComboBox1.text
    
    iNext = 0
    
    On Error Resume Next
    Set selSet = ThisDrawing.SelectionSets.Item("Attr")
    On Error GoTo 0
    If selSet Is Nothing Then
      Set selSet = ThisDrawing.SelectionSets.Add("Attr")
    End If
    selSet.Clear
    
    selSet.Select acSelectionSetAll, , , iCode, vData
    
    If selSet.Count = 0 Then
      MsgBox "Атрибуты не найдены"
      Exit Sub
    End If
    
    CommandButton1.Caption = "Найти далее"
    
  End If
  
  On Error Resume Next
  Set oAtrDef = selSet(iNext)
  On Error GoTo 0
  If oAtrDef Is Nothing Then
    MsgBox "Поиск закончен"
    CommandButton1.Caption = "Найти"
    sngLeft = Me.Left
    sngTop = Me.top
    Me.Hide
    Me.Show
    Exit Sub
  End If
  
  oAtrDef.GetBoundingBox vMin, vMax
  
  ZoomWindow vMin, vMax
  
  iNext = iNext + 1
  
End Sub

Private Sub CommandButton2_Click()
  End
End Sub

Private Sub TextBox1_KeyPress(ByVal KeyAscii As MSForms.ReturnInteger)
    
  If KeyAscii = 32 Then
    MsgBox "Пробелы нельзя вводить"
    'TextBox1 = VBA.Left(TextBox1, Len(TextBox1) - 1)
    KeyAscii = 0
  End If

End Sub

Private Sub UserForm_Activate()
  
  If sngLeft <> 0 And sngTop <> 0 Then
    Me.Left = sngLeft
    Me.top = sngTop
  End If
  
End Sub

Private Sub UserForm_Terminate()
  On Error Resume Next
  ThisDrawing.SelectionSets.Item("Attr").Delete
End Sub

Private Sub AddNameToCombo()
  
  Dim sName As String
  Dim i As Integer
  
  sName = ComboBox1.text
  
  For i = 0 To ComboBox1.ListCount - 1
    If ComboBox1.List(i, 0) = sName Then
      Exit Sub
    End If
  Next
  
  ComboBox1.AddItem sName
  
End Sub

Attribute VB_Name = "FormSumLine"
Attribute VB_Base = "0{0F11CA9E-DC7F-4B52-8024-6CAFE9502FD9}{81C9EB24-D7F0-4618-A585-C599F4BCE5B2}"
Attribute VB_GlobalNameSpace = False
Attribute VB_Creatable = False
Attribute VB_PredeclaredId = True
Attribute VB_Exposed = False
Attribute VB_TemplateDerived = False
Attribute VB_Customizable = False
Option Explicit

Private Sub cmbExit_Click()
  End
End Sub

Private Sub cmbSelect_Click()
  
  Dim oSumLines As SumLine
  Dim colSumLines As New Collection
  Dim oLine As AcadLine
  Dim selSet As AcadSelectionSet
  Dim iCode(1) As Integer
  Dim vDate(1) As Variant
  Dim dSumLine As Double
  
  Me.Hide
  
  iCode(0) = 0: vDate(0) = "Line"
  iCode(1) = 8: vDate(1) = ComboBoxLayer.text
  
  On Error Resume Next
  ThisDrawing.SelectionSets.Item("Lines").Delete
  On Error GoTo 0
  
  Set selSet = ThisDrawing.SelectionSets.Add("Lines")
  
  selSet.SelectOnScreen iCode, vDate
  
  For Each oLine In selSet
    Set oSumLines = Nothing
    On Error Resume Next
    Set oSumLines = colSumLines(CStr(FormatNumber(oLine.Length, 2)))
    On Error GoTo 0
    If oSumLines Is Nothing Then
      'создаем новый объект суммы линий
      Set oSumLines = New SumLine
      Set oSumLines.oLine = oLine
      oSumLines.iKol = 1
      colSumLines.Add oSumLines, CStr(FormatNumber(oLine.Length, 2))
    Else
      oSumLines.iKol = oSumLines.iKol + 1
    End If
    dSumLine = dSumLine + oLine.Length
  Next
  
  'сортировка длин линий
  SortyrSumLines colSumLines
  ListBoxLines.Clear
  For Each oSumLines In colSumLines
    ListBoxLines.AddItem FormatNumber(oSumLines.oLine.Length, 2)
    ListBoxLines.List(ListBoxLines.ListCount - 1, 1) = oSumLines.iKol
  Next
  
  TextBoxSumLine.text = FormatNumber(dSumLine, 2)
  
  selSet.Delete
  
  Me.Show
  
End Sub

Private Sub UserForm_Initialize()
  
  Dim oLayer As AcadLayer
  
  'заполнение комбобокса слоев
  ComboBoxLayer.AddItem "На всех слоях"
  For Each oLayer In ThisDrawing.Layers
    ComboBoxLayer.AddItem oLayer.Name
  Next
  ComboBoxLayer.ListIndex = 0
      
End Sub

Private Function SortyrSumLines(colLines As Collection)
  
  Dim i As Integer
  Dim j As Integer
  Dim oSumLine As SumLine
  
  For i = 1 To colLines.Count
    For j = 1 To colLines.Count - i
      If colLines(j).oLine.Length < colLines(j + 1).oLine.Length Then
        Set oSumLine = colLines(j)
        colLines.Remove j
        colLines.Add oSumLine, FormatNumber(oSumLine.oLine.Length, 2), , j
      End If
    Next
  Next
  
  
End Function

Attribute VB_Name = "Main"
Option Explicit
  
  Public Const pcsVBProjectName As String = "AllOther"
  
'общие процедуры

'очистка чертежа
Public Sub PurgeALL()
  ThisDrawing.PurgeALL
End Sub


Public Sub SumLine()
  'вычисление суммы длин всех выбранных линий на определенном слое
  
  FormSumLine.Show
  
End Sub

Public Sub FindAtr()
  'Поиск атрибутов (в схемах изделий)
  FormFindAtr.Show
  
End Sub

Public Sub AttrLockPos()
  'Снятие фиксации позиции атрибута у блоков свай (Pile)
  
  Dim dWidthFactor As Double
  dWidthFactor = 0.8
  
  Dim selSet As AcadSelectionSet
  Dim iCode(0) As Integer
  Dim vDate(0) As Variant
  
  'Выбор всех блоков свай (Like Pile*)
  On Error Resume Next
  Set selSet = ThisDrawing.SelectionSets.Item("Pile")
  If selSet Is Nothing Then
    Set selSet = ThisDrawing.SelectionSets.Add("Pile")
  Else
    selSet.Clear
  End If
  
  iCode(0) = 0: vDate(0) = "insert"
  
  selSet.Select acSelectionSetAll, , , iCode, vDate
  
  Dim oEnt As AcadEntity
  Dim oBlRef As AcadBlockReference
  Dim oAtrRef As AcadAttributeReference
  Dim oAtr As AcadAttribute
  Dim oBl As AcadBlock
  Dim oEnty As AcadEntity
  Dim oBlRefPipe As AcadBlockReference
  Dim oLayer As AcadLayer
  Dim bLocked As Boolean
  Dim bok As Boolean
  Dim varAtrPt As Variant
   Dim dAtrRot As Double
   Dim vAttrs As Variant
   Dim i As Integer
  
  For Each oLayer In ThisDrawing.Layers
    If oLayer.Name = "0" Then
      ThisDrawing.ActiveLayer = oLayer
      Exit For
    End If
  Next
  
  For Each oEnt In selSet
    If TypeOf oEnt Is AcadBlockReference Then
      Set oBlRef = oEnt
      Set oLayer = ThisDrawing.Layers(oBlRef.Layer)
      oLayer.Lock = False
      If oBlRef.Name Like ("Pile*") Then
        If oBlRef.HasAttributes = True Then
          Set oBl = ThisDrawing.Blocks(oBlRef.Name)
          bLocked = False
          For Each oEnty In oBl
            If TypeOf oEnty Is AcadAttribute Then
              Set oAtr = oEnty
              If oAtr.TagString = "0" Then
                If oAtr.LockPosition = True Then
                    oAtr.LockPosition = False
                    oAtr.ScaleFactor = dWidthFactor
                    bLocked = True
                    Exit For
                End If
              End If
            End If
          Next
          
          'If bLocked = True Then
            bok = False
            vAttrs = oBlRef.GetAttributes
            For i = LBound(vAttrs) To UBound(vAttrs)
                Set oAtrRef = vAttrs(i)
                If oAtrRef.TagString = "0" Then
                    'считываем положение атрибута
                    varAtrPt = oAtrRef.InsertionPoint
                    dAtrRot = oAtrRef.Rotation
                    bok = True
'                    'нужно синхронизировать атрибуты у блока, и повернуть атрибут
'                    ThisDrawing.SendCommand "_AttSync" & vbCr & "_n" & vbCr & oBlRef.Name & vbCr
                    Exit For
                End If
            Next
            If bok = True Then
                'вставляем заново блок
                Set oBlRefPipe = ThisDrawing.ModelSpace.InsertBlock(oBlRef.InsertionPoint, oBlRef.Name, 1, 1, 1, oBlRef.Rotation)
                oBlRef.Delete
                vAttrs = Nothing
                vAttrs = oBlRefPipe.GetAttributes
                For i = LBound(vAttrs) To UBound(vAttrs)
                    Set oAtrRef = vAttrs(i)
                    If oAtrRef.TagString = "0" Then
                        'восстанавливаем положение атрибута
                        oAtrRef.Rotation = dAtrRot
                        oAtrRef.Move oAtrRef.InsertionPoint, varAtrPt
                        oAtrRef.ScaleFactor = dWidthFactor
                        Exit For
                    End If
                Next
            End If
          'End If
        End If
      End If
    End If
  Next
  
End Sub

Attribute VB_Name = "SumLine"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public oLine As AcadLine
Public iKol As Integer
