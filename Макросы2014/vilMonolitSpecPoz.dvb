Attribute VB_Name = "Functions"
Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function SelectBlocksArmElem() As AcadSelectionSet
   'выбор всех блоков с именами из массива asArmBlNames
   
   FillArmBlNames
   
   Dim sset As AcadSelectionSet
   Dim ssetAllBlWithAtr As AcadSelectionSet
   Set sset = Functions.GetSelSet("ArmBlocks")
   Set ssetAllBlWithAtr = Functions.GetSelSet("AllBlocksWithAtr")
   Dim intType(1) As Integer
   Dim varDate(1) As Variant
   
   intType(0) = 0: varDate(0) = "insert"
   intType(1) = 66: varDate(1) = 1
   
   'выбор всех блоков
   ssetAllBlWithAtr.SelectOnScreen intType, varDate
   
   Dim objBlRef As AcadBlockReference
   Dim objAtrRef As AcadAttributeReference
   Dim vAtr As Variant
   Dim bYes As Boolean
   Dim aEntBlRef() As AcadEntity
   Dim colBl As New Collection
   
   'отфильтровываю ненужные блоки
   For Each objBlRef In ssetAllBlWithAtr
      bYes = False
      For j = 0 To UBound(asArmBlNames)
         If LCase(objBlRef.EffectiveName) = LCase(asArmBlNames(j)) Then
            bYes = True
            Exit For
         End If
      Next
      If bYes = True Then
         'заносим блоки в коллекцию
         colBl.Add objBlRef
      End If
   Next
   'удаление набора
   ssetAllBlWithAtr.Delete
   
   If colBl.Count > 0 Then
      'переброс блоков из колекции в массив
      ReDim aEntBlRef(colBl.Count - 1)
      For i = 0 To colBl.Count - 1
         Set aEntBlRef(i) = colBl(i + 1)
      Next
      sset.AddItems aEntBlRef
      
      'очистка колекцуии и массива
      Set colBl = Nothing
      Erase aEntBlRef
   End If
   
   Set SelectBlocksArmElem = sset
   
End Function


Public Function FillArmBlNames()
   
   asArmBlNames(0) = "vil_ArmSter"
   asArmBlNames(1) = "vil_ArmSterRange200"
   asArmBlNames(2) = "vil_ArmSterRange150"
   asArmBlNames(3) = "vil_ArmSterRange100"
   asArmBlNames(4) = "vil_ArmSterRange200_hor"
   asArmBlNames(5) = "vil_ArmSterRange150_hor"
   asArmBlNames(6) = "vil_ArmSterRange100_hor"
   asArmBlNames(7) = "vil_ArmSterRange200_vertic"
   asArmBlNames(8) = "vil_ArmSterRange150_vertic"
   asArmBlNames(9) = "vil_ArmSterRange100_vertic"
   asArmBlNames(10) = "vil_ArmSter_leader"
   
End Function

Public Function GetLayer(strLayerName As String) As AcadLayer
   'возвращает объект слоя, с заданным именем
   'если слоя с таким именем не было, он создается
   
   On Error GoTo HasError
   Set GetLayer = ThisDrawing.Layers.Item(strLayerName)
   GetLayer.Lock = False
   If Not GetLayer Is ThisDrawing.ActiveLayer Then
      GetLayer.Freeze = False
   End If
   
Exit Function

HasError:
   Set GetLayer = ThisDrawing.Layers.Add(strLayerName)
   
End Function

Attribute VB_Name = "Main"
Option Explicit
   
   'массив имен блоков арм.элементов. Заполняется Functions.FillArmBlNames
   Public asArmBlNames(10) As String
   
Public Sub Main()

   Const iColumnNaimen As Integer = 2
   Const iColumnPoz As Integer = 0
   Const iColumnKol As Integer = 3
   Const iColumnPrim As Integer = 4
   
   Dim sOtchet As String
         
   Dim objTable As Object
   Dim table As AcadTable
   Dim objBlRef As AcadBlockReference
   Dim objAtrRef As AcadAttributeReference
   Dim rows As Integer
   Dim i As Integer
   Dim j As Integer
   Dim sNaimen As String
   Dim sNaimenNext As String
   Dim iKol As Integer
   Dim iKolNext As Integer
   Dim dMassa As Double
   Dim dMassaNext As Double
   Dim asNaimens() As String
   Dim bNext As Boolean
   Dim vPt As Variant
   Dim iRowData As Integer
   Dim iPoz As Integer
   Dim bYes As Boolean
   Dim vAtr As Variant
   
   On Error GoTo HasError
   
'   'Напоминание
'   If MsgBox("Простановка позиций в спецификации по порядку," & _
'         "заполнения атрибутов в блоках арм.элементов на чертеже. " & vbCrLf & _
'         "В таблице разделитель дробной части числа должен соответствовать системным установкам Windows." & vbCrLf & _
'         "Продожить?", vbYesNo + vbInformation, "vilMonolitSpecPoz") = vbNo Then
'      Exit Sub
'   End If
   
'***********************************************************************************************
'********* 1. ПРОСТАНОВКА ПОЗ В ТАБЛИЦЕ ********************************************************
'***********************************************************************************************
         
   'запрос таблицы
   ThisDrawing.Utility.GetEntity objTable, vPt, "Выберете таблицу:"
   
   If TypeOf objTable Is AcadTable Then
      Set table = objTable
      'определение номера первой строки значений (может быть 1 строка - название, 2 - заголовки, 3 - данные)
      bNext = False
      Do While bNext = False
         For i = 0 To 10
            Dim stest As String
            stest = table.GetCellValue(i, iColumnPoz)
            If InStr(stest, "Поз") > 0 Then
               iRowData = i + 1
               bNext = True
               Exit For
            End If
         Next
         bNext = True
      Loop
      If iRowData = 0 Then
         MsgBox "Строка Поз не определена."
         Exit Sub
      End If
      
      '//
      '// Удаление столбцов Диаметр, Класс, Длина стержня (5,6,7)
      '//
      table.DeleteColumns 5, 3
      
      'перебор строк и объединение по наименованию.
      'Поз, Обозн, Наименование, Кол, Масса Ед, Масса общ.
      rows = table.rows - iRowData 'кол-во строк с данными (целое число строк)
      
      ReDim asNaimens(rows - 1)
      iPoz = 0
      
      For i = iRowData To table.rows - 1
         sNaimen = table.GetCellValue(i, iColumnNaimen)
         iKol = table.GetCellValue(i, iColumnKol)
'         dMassa = Val(table.GetCellValue(i, iColumnPrim))
         bNext = False
         Do While bNext = False
            'след.строка
            'проверка есть ли след строка
            If i + 1 <= table.rows - 1 Then
               sNaimenNext = table.GetCellValue(i + 1, iColumnNaimen)
               'проверка равенства строк
               If Strings.StrComp(LCase(sNaimen), LCase(sNaimenNext), vbTextCompare) = 0 Then
                  iKolNext = table.GetCellValue(i + 1, iColumnKol)
'                  dMassaNext = Valtable.GetCellValue(i + 1, iColumnPrim)
                  iKol = iKol + iKolNext
'                  dMassa = dMassa + dMassaNext
                  'удаляем строку
                  table.DeleteRows i + 1, 1
                  'i = i - 1
               Else
                  bNext = True
               End If
            Else
               bNext = True
            End If
         Loop
         'заполняем Поз
         iPoz = iPoz + 1
         table.SetCellValue i, iColumnPoz, iPoz
         'заполняем кол и массу
         table.SetCellValue i, iColumnKol, iKol
'         table.SetCellValue i, iColumnPrim, FormatNumber(dMassa, 2, vbTrue, vbTrue, vbTrue) & " кг"
         'записываем наимен в коллекцию
         asNaimens(iPoz - 1) = sNaimen
      Next
   End If
   
   'очистка объектов
   Set objTable = Nothing
   Set table = Nothing
   
   sOtchet = "Позиции успешно проставлены!"
   
'*************************************************************************************************
'******** 2. Заполнение атрибутов ПОЗ в блоках арм. элементов ************************************
'*************************************************************************************************

   'составляем коллекцию с наименнованиями
   Dim colNaimens As New Collection
   Dim vNaimen As Variant
   
   For Each vNaimen In asNaimens
      If vNaimen <> "" Then
         colNaimens.Add vNaimen
      End If
   Next
   If colNaimens.Count = 0 Then
      sOtchet = sOtchet & vbCrLf & "В таблице найдено 0 наименований."
      GoTo Otchet
   End If
   'очищаем массив наименования
   Erase asNaimens
   
   'заполнение атриб.Поз у блоков арм.элементов
   
   'выбор всех блоков с именами из массива asArmBlNames
   Dim sset As AcadSelectionSet
   Set sset = Functions.SelectBlocksArmElem
   
   If sset.Count = 0 Then
      sOtchet = sOtchet & vbCrLf & " Блоки арм.элементов не найдены."
      GoTo Otchet
   End If
   
      Dim iPozZap As Integer
      
      For Each objBlRef In sset
         'находим атр.наименования
         bYes = False
         For Each vAtr In objBlRef.GetAttributes
            Set objAtrRef = vAtr
            If LCase(objAtrRef.TagString) = "наименование" Then
               'находим поз для этого наименования
               For i = 0 To colNaimens.Count - 1
                  If LCase(objAtrRef.TextString) = LCase(colNaimens(i + 1)) Then
                     bYes = True
                     Exit For
                  End If
               Next
               If bYes = True Then Exit For
            End If
         Next
         'заполняем атр.поз
         If bYes = True Then
            For Each vAtr In objBlRef.GetAttributes
               Set objAtrRef = vAtr
               If LCase(objAtrRef.TagString) = "поз" Then
                  objAtrRef.TextString = i + 1
                  iPozZap = iPozZap + 1
                  Exit For
               End If
            Next
         End If
      Next
   
   
   sOtchet = sOtchet & vbCrLf & " Найдено " & sset.Count & " блоков арм.элементов на чертеже." & vbCrLf & _
            "Заполнено " & iPozZap & " атрибута ПОЗ."

Otchet:
   MsgBox sOtchet, vbOKOnly, "vilMonolitSpecPoz"
   
   Exit Sub
   
HasError:
   MsgBox Err.Description
   
End Sub

Public Sub InsertVynoska()
   'вставка блока Позиционной выноски в точки вставки блоков арм.элементов
   'заполнение Поз выноски из атриб.поз блока
   
   Const csVynoskaBlName As String = "vil_Leader"
   Const csBlVynoskaPath As String = "\\Sgpsrv2\СПД\Конструкторы\БЛОКИ\Блоки арматуры\vilBlocksArm.dwg"
   Const csLayerVynosok As String = "Размеры"
   
   Dim oLayerVyn As AcadLayer
   Dim ssetBlArmEl As AcadSelectionSet
   Dim oBl As AcadBlock
   Dim oBlRef As AcadBlockReference
   Dim oBlRefVynoska As AcadBlockReference
   Dim oAtrRef As AcadAttributeReference
   Dim aoDynProp() As AcadDynamicBlockReferenceProperty
   Dim colDynBlRefProp As New Collection
   Dim dInsPt0(2) As Double
   Dim vInsPt As Variant
   Dim vAtr As Variant
   Dim sPoz As String
   Dim sShag As String
   Dim i As Integer
   Dim iCountBlVyn As Integer
   Dim bYes As Boolean
   
   'выбор всех блоков арм.элементов
   Set ssetBlArmEl = Functions.SelectBlocksArmElem
   
'*****************************************************************
'******** Определение блока выноски в текущем чертеже ************

   'есть ли блок выноски в чертеже
   bYes = False
   For Each oBl In ThisDrawing.Blocks
      If LCase(oBl.Name) = LCase(csVynoskaBlName) Then
         bYes = True
         Exit For
      End If
   Next
   If bYes = False Then
      'определяем запись блока в чертеже из файла с блоком выноски
      'проверка наличия файла с блоком
      If Dir(csBlVynoskaPath) = "" Then
         'файла нет
         MsgBox "Файл с блоком выноски не найден." & vbCrLf & csBlVynoskaPath
         Exit Sub
      End If
      'вставка файла с блоком выноски и сразу удаляем, определения всех блоков в этом файле останутся
      Set oBlRef = ThisDrawing.ModelSpace.InsertBlock(dInsPt0, csBlVynoskaPath, 1#, 1#, 1#, 0)
      oBlRef.Delete
      bYes = False
      For Each oBl In ThisDrawing.Blocks
         If LCase(oBl.Name) = LCase(csVynoskaBlName) Then
            bYes = True
            Exit For
         End If
      Next
      If bYes = False Then
         MsgBox "Блок выноски в заданном файле не определен." & vbCrLf & csBlVynoskaPath
         Exit Sub
      End If
   End If
   
   
'***********************************************************************************************************************
'******** Перебор всех блоков арм.элем и вставка блока выноски в точку вставки с заполнением поз ("верхняя") ***********

   iCountBlVyn = 0
   For Each oBlRef In ssetBlArmEl
      'точка вставки
      vInsPt = oBlRef.InsertionPoint
      'определяем атрибут поз.
      sPoz = ""
      For Each vAtr In oBlRef.GetAttributes
         Set oAtrRef = vAtr
         If LCase(oAtrRef.TagString) = "поз" Then
            sPoz = oAtrRef.TextString
            Exit For
         End If
      Next
      'определяем параметр дин.блока шаг????
      sShag = ""
      If oBlRef.IsDynamicBlock Then
         aoDynProp = oBlRef.GetDynamicBlockProperties
         For i = 0 To UBound(aoDynProp)
            If LCase(aoDynProp(i).PropertyName) = "шаг" Then
               sShag = aoDynProp(i).Value
               Exit For
            End If
         Next
      End If
      
      'вставляем блок выноски
      'определяем слой для выносок
      Set oLayerVyn = Functions.GetLayer(csLayerVynosok)
      'вставка блока выносчки
      Set oBlRefVynoska = ThisDrawing.ModelSpace.InsertBlock(vInsPt, csVynoskaBlName, 1#, 1#, 1#, 0)
      iCountBlVyn = iCountBlVyn + 1
      oBlRefVynoska.Layer = oLayerVyn.Name
      'заполняем строки выноски
      For Each vAtr In oBlRefVynoska.GetAttributes
         Set oAtrRef = vAtr
         If LCase(oAtrRef.TagString) = "верхняя" Then
            'Поз
            oAtrRef.TextString = sPoz
         End If
         If sShag <> "" Then
            If LCase(oAtrRef.TagString) = "нижняя" Then
               'Шаг
               oAtrRef.TextString = "Шаг " & sShag
            End If
         End If
      Next
   Next
   
   MsgBox "Найдено " & ssetBlArmEl.Count & " блоков арм.элементов." & vbCrLf & _
         "Вставлено " & iCountBlVyn & " блоков выносок.", , "vilMonolitSpecPoz"
   
End Sub
