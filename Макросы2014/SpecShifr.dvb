Attribute VB_Name = "FormSpecForSel"
Attribute VB_Base = "0{07A12813-A2CE-461E-9E80-2320D2273317}{6B71C27A-0FD1-4B44-A99E-7933DEF8E995}"
Attribute VB_GlobalNameSpace = False
Attribute VB_Creatable = False
Attribute VB_PredeclaredId = True
Attribute VB_Exposed = False
Attribute VB_TemplateDerived = False
Attribute VB_Customizable = False
Option Explicit

Private Sub ButtonAddSpec_Click()
  
   Dim objBlCon As clConstr
   Dim objTable As AcadTable
   Dim vPtTable As Variant
   Dim intRow As Integer
    
  Me.Hide
    
      ThisDrawing.ActiveLayer.LayerOn = True
      ThisDrawing.ActiveLayer.Lock = False
      'запрашиваем точку вставки таблы
      FormaPoShifru.Hide
      vPtTable = ThisDrawing.Utility.GetPoint(, "Верхний левый угол")
      Set objTable = ThisDrawing.ModelSpace.AddTable(vPtTable, 3, 7, 8, 10)
      objTable.StyleName = "Спецификация"
      objTable.RegenerateTableSuppressed = True
      objTable.SetRowHeight 0, 10
'      objTable.SetCellValue 0, 0, "Спецификация Блоков с шифром - " & strShifr
      objTable.SetRowHeight 1, 15
      objTable.SetRowHeight 2, 8
      objTable.SetCellValue 1, 0, "№ п/п"
      objTable.SetColumnWidth 0, 15
      objTable.SetCellValue 1, 1, "Обозначение"
      objTable.SetColumnWidth 1, 40
      objTable.SetCellValue 1, 2, "Наименование"
      objTable.SetColumnWidth 2, 40
      objTable.SetCellValue 1, 3, "Имя"
      objTable.SetColumnWidth 3, 30
      objTable.SetCellValue 1, 4, "Кол"
      objTable.SetColumnWidth 4, 15
      objTable.SetCellValue 1, 5, "Масса"
      objTable.SetColumnWidth 5, 15
      objTable.SetCellValue 1, 6, "Примечание"
      objTable.SetColumnWidth 6, 25
      intRow = 2
      For Each objBlCon In objShifrBl.colBlocksConstr
         'заполняем таблицу
         objTable.SetText intRow, 0, intRow - 1
         objTable.SetText intRow, 1, strShifr
         objTable.SetText intRow, 2, objBlCon.Naimen
         objTable.SetText intRow, 3, objBlCon.BlName
         objTable.SetText intRow, 4, objBlCon.colBlocks.Count
         objTable.SetText intRow, 5, objBlCon.Massa
         
         intRow = intRow + 1
         objTable.InsertRows intRow, 8, 1
      Next
      objTable.ScaleEntity vPtTable, CDbl(FormaPoShifru.TextBoxM)
      objTable.RegenerateTableSuppressed = False
'      ThisDrawing.Regen acActiveViewport
   
   Me.Show
  
End Sub

Private Sub ButtonExite_Click()
  Me.Hide
End Sub

Private Sub ButtonShowBlock_Click()
  
  Dim index As Integer
  Dim objBlRef As AcadBlockReference
   
  index = ListBoxGBI.ListIndex
  If index <> -1 Then
     Set objBlRef = ListBoxGBI.Selected
     objBlRef.Highlight True
     ZoomCenter objBlRef.InsertionPoint, 10000
  End If
  
End Sub

Private Sub ButtonShowBlockNeopr_Click()
  
  Dim index As Integer
  Dim objBlRef As AcadBlockReference
   
  index = ListBoxNeopr.ListIndex
  If index <> -1 Then
     Set objBlRef = ListBoxNeopr.Item(index + 1)
     objBlRef.Highlight True
     ZoomCenter objBlRef.InsertionPoint, 10000
  End If
  
End Sub


Private Sub UserForm_Initialize()
  
  Dim oBlRef As AcadBlockReference
  
  For Each oBlRef In selSetBlockGBIzd
    
    ListBoxGBI.AddItem oBlRef.Name
    
  Next
  
  For Each oBlRef In colNeopredGBIzd
    
    ListBoxNeopr.AddItem oBlRef.Name
    
  Next
  
End Sub

Attribute VB_Name = "FormaPoShifru"
Attribute VB_Base = "0{A035B8F6-F0FD-405D-B3F9-3A12FE907428}{239CED6A-8E23-4FA8-B64A-BDBFB4CDD3BA}"
Attribute VB_GlobalNameSpace = False
Attribute VB_Creatable = False
Attribute VB_PredeclaredId = True
Attribute VB_Exposed = False
Attribute VB_TemplateDerived = False
Attribute VB_Customizable = False
Option Explicit
   
   Dim colShifrRef As New Collection 'коллекция объектов clShifrsBl
'   Dim colNeopredGBIzd As New Collection 'неопределенные жб изделия
      
Private Sub cmbExit_Click()
   Hide
End Sub

Private Sub cmbSpec_Click()
   'построить спеку для этого шифра
   
   Dim strShifr As String
   Dim objShifrBl As clShifrBl
   Dim objBlCon As clConstr
   Dim objTable As AcadTable
   Dim vPtTable As Variant
   Dim intRow As Integer
    
   strShifr = ListBoxShifr.Text
   If strShifr <> "" Then
      Set objShifrBl = colShifrRef.Item(strShifr)
      ThisDrawing.ActiveLayer.LayerOn = True
      ThisDrawing.ActiveLayer.Lock = False
      'запрашиваем точку вставки таблы
      FormaPoShifru.Hide
      vPtTable = ThisDrawing.Utility.GetPoint(, "Верхний левый угол")
      Set objTable = ThisDrawing.ModelSpace.AddTable(vPtTable, 3, 7, 8, 10)
      objTable.StyleName = "Спецификация"
      objTable.RegenerateTableSuppressed = True
      objTable.SetRowHeight 0, 10
      objTable.SetCellValue 0, 0, "Спецификация Блоков с шифром - " & strShifr
      objTable.SetRowHeight 1, 15
      objTable.SetRowHeight 2, 8
      objTable.SetCellValue 1, 0, "№ п/п"
      objTable.SetColumnWidth 0, 15
      objTable.SetCellValue 1, 1, "Обозначение"
      objTable.SetColumnWidth 1, 40
      objTable.SetCellValue 1, 2, "Наименование"
      objTable.SetColumnWidth 2, 40
      objTable.SetCellValue 1, 3, "Имя"
      objTable.SetColumnWidth 3, 30
      objTable.SetCellValue 1, 4, "Кол"
      objTable.SetColumnWidth 4, 15
      objTable.SetCellValue 1, 5, "Масса"
      objTable.SetColumnWidth 5, 15
      objTable.SetCellValue 1, 6, "Примечание"
      objTable.SetColumnWidth 6, 25
      intRow = 2
      For Each objBlCon In objShifrBl.colBlocksConstr
         'заполняем таблицу
         objTable.SetText intRow, 0, intRow - 1
         objTable.SetText intRow, 1, strShifr
         objTable.SetText intRow, 2, objBlCon.Naimen
         objTable.SetText intRow, 3, objBlCon.BlName
         objTable.SetText intRow, 4, objBlCon.colBlocks.Count
         objTable.SetText intRow, 5, objBlCon.Massa
         
         intRow = intRow + 1
         objTable.InsertRows intRow, 8, 1
      Next
      objTable.ScaleEntity vPtTable, CDbl(FormaPoShifru.TextBoxM)
      objTable.RegenerateTableSuppressed = False
'      ThisDrawing.Regen acActiveViewport
      FormaPoShifru.Show
   Else
      MsgBox "Нужно выбрать шифр"
   End If
   
End Sub

Private Sub cmbViewHigh_Click()
   
   Dim strBlName As String
   Dim objShifrBl As clShifrBl
   Dim strShifr As String
   Dim objBlCon As clConstr
   Dim objBlockRef As AcadBlockReference
   Dim intKey As Integer
      
   strShifr = ListBoxShifr.Text
   strBlName = ListBoxBlocks.Text
   intKey = ListBoxBlForPrev.ListIndex
   If intKey <> -1 Then
      Set objShifrBl = colShifrRef.Item(strShifr)
      Set objBlCon = objShifrBl.colBlocksConstr.Item(strBlName)
      Set objBlockRef = objBlCon.colBlocks.Item(CStr(intKey))
      objBlockRef.Highlight True
      ZoomCenter objBlockRef.InsertionPoint, 10000
   Else
      MsgBox "Выберете блок который нужно показать"
   End If
   
End Sub

Private Sub cmbViewNeopr_Click()
   
   Dim index As Integer
   Dim objBlRef As AcadBlockReference
   
   index = ListBoxNeopred.ListIndex
   If index <> -1 Then
      Set objBlRef = colNeopredGBIzd.Item(index + 1)
      objBlRef.Highlight True
      ZoomCenter objBlRef.InsertionPoint, 10000
   End If
      
End Sub

Private Sub cmbViewZoom_Click()
   
   Dim strBlName As String
   Dim strShifr As String
   Dim objShifrBl As clShifrBl
   Dim objBlCon As clConstr
   Dim objBlockRef As AcadBlockReference
   Dim intKey As Integer
      
   strShifr = ListBoxShifr.Text
   strBlName = ListBoxBlocks.Text
   intKey = ListBoxBlForPrev.ListIndex
   If intKey <> -1 Then
      Set objShifrBl = colShifrRef.Item(strShifr)
      Set objBlCon = objShifrBl.colBlocksConstr.Item(strBlName)
      Set objBlockRef = objBlCon.colBlocks.Item(CStr(intKey))
      objBlockRef.Highlight True
      ZoomCenter objBlockRef.InsertionPoint, 5000
   Else
      MsgBox "Выберете блок который нужно показать"
   End If
   
End Sub

Private Sub cmbZoomAll_Click()
   ZoomAll
End Sub

Private Sub ListBoxBlocks_Click()
   'выводим инфу для выбранного блока
   
   Dim strBlName As String
   Dim strShifr As String
   Dim objShifrBl As clShifrBl
   Dim objBlCon As clConstr
   Dim objBlockRef As AcadBlockReference
   Dim intKey As Integer
   
   ListBoxBlForPrev.Clear
   
   strShifr = ListBoxShifr.Text
   strBlName = ListBoxBlocks.Text
   
   If strBlName <> "" Then
      Set objShifrBl = colShifrRef.Item(strShifr)
      Set objBlCon = objShifrBl.colBlocksConstr.Item(strBlName)
      TextBoxBlName = objBlCon.BlName
      TextBoxMassa = objBlCon.Massa
      TextBoxNaimen = objBlCon.Naimen
      TextBoxObozn = strShifr
      For Each objBlockRef In objBlCon.colBlocks
         ListBoxBlForPrev.AddItem objBlockRef.Name, intKey
         intKey = intKey + 1
      Next
   End If
   
   If ListBoxBlForPrev.ListCount <> 0 Then
      LabelKolvoBl = "Кол-во блоков: " & ListBoxBlForPrev.ListCount
   End If
   
End Sub

Private Sub ListBoxNeopred_Click()
   'выводим инфу по блоку
   
   Dim index As Integer
   Dim objBlRef As AcadBlockReference
   Dim varAtr As Variant
   Dim objAtr As AcadAttributeReference
   
   index = ListBoxNeopred.ListIndex
   If index <> -1 Then
      Set objBlRef = colNeopredGBIzd.Item(index + 1)
      TextBoxBlName = objBlRef.Name
      For Each varAtr In objBlRef.GetAttributes
         Set objAtr = varAtr
         Select Case objAtr.Layer
            Case "Att~Massa"
               TextBoxMassa = objAtr.TextString
            Case "Att~Naimen"
               TextBoxNaimen = objAtr.TextString
            Case "Att~Obozn"
               TextBoxObozn = objAtr.TextString
         End Select
      Next
   End If
   
End Sub

Private Sub ListBoxShifr_Click()
   'выводим список блоков для выделенного шифра
   
   Dim strShifr As String
   Dim objShifrBl As clShifrBl
   Dim objBlCon As clConstr
   Dim intKolBlInShifr As Integer
   
   ListBoxBlocks.Clear
   ListBoxBlForPrev.Clear
   
   strShifr = ListBoxShifr.Text
   If strShifr <> "" Then
      Set objShifrBl = colShifrRef.Item(strShifr)
      'сортировка
      SortyrBlShifr objShifrBl
      For Each objBlCon In objShifrBl.colBlocksConstr
         ListBoxBlocks.AddItem objBlCon.BlName
         intKolBlInShifr = intKolBlInShifr + objBlCon.colBlocks.Count
      Next
      LabelShifrBlKol = "Всего блоков этого шифра: " & intKolBlInShifr
   End If
   
End Sub

Private Sub SortyrBlShifr(ByRef objShifrBl As clShifrBl)
   
   Dim objBlCon1 As clConstr
   Dim objBlCon2 As clConstr
   Dim objBlConTemp As clConstr
   Dim i As Integer
   Dim j As Integer
   Dim intKolvo As Integer
   Dim colBl As Collection
   
   intKolvo = objShifrBl.colBlocksConstr.Count
   Set colBl = objShifrBl.colBlocksConstr
   
   For i = 1 To intKolvo - 1
      For j = 1 To intKolvo - 1
         'по наименованию
         Set objBlCon1 = colBl.Item(j)
         Set objBlCon2 = colBl.Item(j + 1)
         If StrComp(objBlCon1.Naimen, objBlCon2.Naimen, vbTextCompare) = 1 Then
            Set objBlConTemp = objBlCon1
            colBl.Remove j
            colBl.Add objBlConTemp, objBlConTemp.BlName, , j
         ElseIf StrComp(objBlCon1.Naimen, objBlCon2.Naimen, vbTextCompare) = 0 Then
            'сортируем по имени блока
            If StrComp(objBlCon1.BlName, objBlCon2.BlName, vbTextCompare) = 1 Then
               Set objBlConTemp = objBlCon1
               colBl.Remove j
               colBl.Add objBlConTemp, objBlConTemp.BlName, , j
            End If
         End If
      Next
   Next
   
End Sub

Private Sub UserForm_Initialize()
   'составляем массив шифров чертежа
   
   Dim selSetAllBlockAtt As AcadSelectionSet
   Dim selSetAllBlockGBIzd As AcadSelectionSet
   Dim objBlockRef As AcadBlockReference
   Dim objBlockRefs(0) As AcadBlockReference
   Dim objAtr As AcadAttributeReference
   Dim intFT(1) As Integer
   Dim varFD(1) As Variant
   Dim varAtr As Variant
   Dim objBlShifrRef As clShifrBl
   
   'выбор всех блоков с атрибутами
   Set selSetAllBlockAtt = Fun.GetSelSet("Все блоки с атрибутами")
   'устанавливаем фильтр блоков с атрибутами
   intFT(0) = 0: varFD(0) = "insert"
   intFT(1) = 66: varFD(1) = 1
   'выбор
   selSetAllBlockAtt.Select acSelectionSetAll, , , intFT, varFD
   
   'составляем набор блоков жб изделий
   Set selSetAllBlockGBIzd = Fun.GetSelSet("Все блоки жб изделий")
   'отбираем из всех блоков с атриб-ми жб изделия
   For Each objBlockRef In selSetAllBlockAtt
      For Each varAtr In objBlockRef.GetAttributes
         Set objAtr = varAtr
         If objAtr.Layer = "Att~Material" Then
            If objAtr.TextString = "Железобетон" Then
               'добавляем в набор блоков жб изделий
               Set objBlockRefs(0) = objBlockRef
               selSetAllBlockGBIzd.AddItems objBlockRefs
            Else
               'заносим в коллекцию блоков с атрибутами не определенные как жб изделие
               colNeopredGBIzd.Add objBlockRef
            End If
            Exit For 'выходим из перебора атрибутов
         End If
      Next
   Next
   Erase objBlockRefs
   Set selSetAllBlockAtt = Nothing
   
   Dim strValue As String
   
   'из полученного набора всех жб изделий составляем коолекцию блоков по шифрам-ссылкам
   For Each objBlockRef In selSetAllBlockGBIzd
      For Each varAtr In objBlockRef.GetAttributes
         Set objAtr = varAtr
         If objAtr.Layer = "Att~Obozn" Then
            strValue = objAtr.TextString
            Set objBlShifrRef = Nothing
            On Error Resume Next
            Set objBlShifrRef = colShifrRef.Item(strValue)
            On Error GoTo 0
            If objBlShifrRef Is Nothing Then
               Set objBlShifrRef = New clShifrBl
               objBlShifrRef.ShifrRef = objAtr.TextString
               objBlShifrRef.AddBlock objBlockRef
               colShifrRef.Add objBlShifrRef, strValue
            Else
               objBlShifrRef.AddBlock objBlockRef
            End If
            Exit For
         End If
      Next
   Next
   
   'сортируем шифры
   SortyrShifr colShifrRef
   
   'выводим список шифров
   For Each objBlShifrRef In colShifrRef
      ListBoxShifr.AddItem objBlShifrRef.ShifrRef
   Next
   
   'выводим список неопределенных блоков
   For Each objBlockRef In colNeopredGBIzd
      ListBoxNeopred.AddItem objBlockRef.Name
   Next
   
   'подгружаем табличный стиль
   'если есть табл.стил="Спецификация", то создавать не нужно
   MakeTableStyleForSpec
   
End Sub

Private Sub SortyrShifr(ByRef colShifrRef As Collection)
   
   Dim i As Integer
   Dim j As Integer
   Dim k As Integer
   Dim l As Integer
   Dim intKolvo1 As Integer
   Dim objShifr1 As clShifrBl
   Dim objShifr2 As clShifrBl
   Dim objShifrTemp As clShifrBl
   
   intKolvo1 = colShifrRef.Count
   
   For i = 1 To intKolvo1 - 1
      For j = 1 To intKolvo1 - 1
         Set objShifr1 = colShifrRef.Item(j)
         Set objShifr2 = colShifrRef.Item(j + 1)
         If StrComp(objShifr1.ShifrRef, objShifr2.ShifrRef, vbTextCompare) = 1 Then
            Set objShifrTemp = objShifr1
            colShifrRef.Remove j
            colShifrRef.Add objShifrTemp, objShifrTemp.ShifrRef, , j
         End If
      Next
   Next
   
End Sub

Attribute VB_Name = "Fun"
Option Explicit


Public Function GetSelSet(SelName As String) As AcadSelectionSet
   
   On Error GoTo HasError
   
   Set GetSelSet = ThisDrawing.SelectionSets.Item(SelName)
   GetSelSet.Clear
   
   Exit Function

HasError:
   
   Set GetSelSet = ThisDrawing.SelectionSets.Add(SelName)
   
End Function


Public Function MakeTableStyleForSpec() As String
   'создание табличного стиля для спецификаций
   'для масштаба 1:1, в конкретных условиях нужно отмасштабировать после заполнения
   
   Const strTableStyleName = "Спецификация"
   Const strTextStyleName = "Спецификаций"
   
   Dim objTableStyle As AcadTableStyle
   Dim objTextStyle As AcadTextStyle
   Dim objDictTableStyle As AcadDictionary
   Dim bolYes As Boolean
   
   'создаем табличный стиль в словаре чертежа
   Set objDictTableStyle = ThisDrawing.Dictionaries.Item("ACAD_TABLESTYLE")
   
   'проверяем есть ли уже такой табл стиль
   For Each objTableStyle In objDictTableStyle
      If objTableStyle.Name = strTableStyleName Then
         'переделывать не буду ????????????
         Exit Function
      End If
   Next
'   On Error Resume Next 'не хорошо конечно, надо сделать проверки
   Set objTableStyle = objDictTableStyle.AddObject(strTableStyleName, "AcDbTableStyle")
   
   'создаем текстовый стиль для таблиц
   For Each objTextStyle In ThisDrawing.TextStyles
      If objTextStyle.Name = strTextStyleName Then
         bolYes = True
      End If
   Next
   If bolYes = False Then
      Set objTextStyle = ThisDrawing.TextStyles.Add(strTextStyleName)
      'задаем шрифт, у нас принят ариал
      objTextStyle.SetFont "Arial", False, False, 0, 34 'значения получил по GetFont для нужного стиля
   End If
'   On Error GoTo 0

   'настраиваем таблицу
   'задаем текстовый стиль всем типам ячеек
   objTableStyle.SetTextStyle AcRowType.acDataRow + AcRowType.acHeaderRow _
                           + AcRowType.acTitleRow + AcRowType.acUnknownRow, strTextStyleName
   'задаем высоту текста
   objTableStyle.SetTextHeight AcRowType.acDataRow + AcRowType.acUnknownRow, 2.5
   objTableStyle.SetTextHeight AcRowType.acHeaderRow + AcRowType.acTitleRow, 3
   'задаем выравниваниев ячейках
   objTableStyle.SetAlignment AcRowType.acHeaderRow + AcRowType.acTitleRow, acMiddleCenter
   objTableStyle.SetAlignment AcRowType.acDataRow + AcRowType.acUnknownRow, acMiddleLeft
   'задаем отступы в ячейках
   objTableStyle.HorzCellMargin = 1.5
   objTableStyle.VertCellMargin = 1
   'задаем толщины границ
   objTableStyle.SetGridLineWeight AcGridLineType.acHorzBottom + AcGridLineType.acHorzInside + AcGridLineType.acHorzTop _
                + AcGridLineType.acVertInside + AcGridLineType.acVertLeft + AcGridLineType.acVertRight, _
                AcRowType.acTitleRow + AcRowType.acHeaderRow, AcLineWeight.acLnWt050
   objTableStyle.SetGridLineWeight AcGridLineType.acHorzBottom + AcGridLineType.acHorzTop + _
               AcGridLineType.acVertInside + AcGridLineType.acVertLeft + AcGridLineType.acVertRight, _
               AcRowType.acDataRow + AcRowType.acUnknownRow, AcLineWeight.acLnWt050
   objTableStyle.SetGridLineWeight AcGridLineType.acHorzInside, _
               AcRowType.acDataRow + AcRowType.acUnknownRow, AcLineWeight.acLnWt025
   'задаем цвет тексту
   Dim color As New AcadAcCmColor
   color.SetRGB 255, 0, 0
   objTableStyle.SetColor AcRowType.acDataRow + AcRowType.acHeaderRow _
                        + AcRowType.acTitleRow + AcRowType.acUnknownRow, color
   
   'вроде все, посмотрим
   
   'возвращаем имя созданного стиля
   MakeTableStyleForSpec = strTableStyleName
   
End Function

Attribute VB_Name = "Main"
Option Explicit

   

'Выбранные блоки. SpecForSelect
Public selSetBlockGBIzd As AcadSelectionSet
Public colNeopredGBIzd As New Collection 'неопределенные жб изделия

Public Sub Main()
   'вывод списка блоков с заданным шифром
         
   FormaPoShifru.Show
   End
End Sub

'Построение спецификации жб изделий для выбранных объектов.
Public Sub SpecForSelect()
  
  Dim selSet As AcadSelectionSet
  Dim intFilterType(1) As Integer
  Dim varFilterDate(1) As Variant
  Dim objBlockRef As AcadBlockReference
  Dim objBlockRefs(0) As AcadBlockReference
  Dim objAtr As AcadAttributeReference
  Dim varAtr As Variant
  Dim objBlShifrRef As clShifrBl
  
  Set selSet = Fun.GetSelSet("SpecForSelect")

  intFilterType(0) = 0: intFilterType(1) = 66
  varFilterDate(0) = "insert": varFilterDate(1) = 1
  
  selSet.SelectOnScreen intFilterType, varFilterDate
  
  If selSet.Count = 0 Then
    MsgBox "Не выбраны блоки с атрибутами."
    End Sub
  End If
  
  'составляем набор блоков жб изделий
   Set selSetBlockGBIzd = Fun.GetSelSet("SpecForSelectGBI")
   'отбираем из всех блоков с атриб-ми жб изделия
   For Each objBlockRef In selSetAllBlockAtt
      For Each varAtr In objBlockRef.GetAttributes
         Set objAtr = varAtr
         If objAtr.Layer = "Att~Material" Then
            If objAtr.TextString = "Железобетон" Then
               'добавляем в набор блоков жб изделий
               Set objBlockRefs(0) = objBlockRef
               selSetBlockGBIzd.AddItems objBlockRefs
            Else
               'заносим в коллекцию блоков с атрибутами не определенные как жб изделие
               colNeopredGBIzd.Add objBlockRef
            End If
            Exit For 'выходим из перебора атрибутов
         End If
      Next
   Next
   Erase objBlockRefs
   Set selSet = Nothing
   
   FormSpecForSel.Show
   Unload FormSpecForSel
   
End Sub

Attribute VB_Name = "clConstr"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

   Dim strBlName As String
   Public colBlocks As New Collection
   Dim intMassa As Integer
   Dim strNaimen As String
   Dim intKey As Integer
   
'имя блка
Public Property Get BlName() As String
   BlName = strBlName
End Property

'масса
Public Property Get Massa() As Integer
   Massa = intMassa
End Property

'наименование
Public Property Get Naimen() As String
   Naimen = strNaimen
End Property

Public Sub AddBlock(objBlockRef As AcadBlockReference)
   colBlocks.Add objBlockRef, CStr(intKey)
   If intKey = 0 Then
      ZapPoley objBlockRef
   End If
   intKey = intKey + 1
   'можно проверять последующие блоки, должно быть все одинаково
End Sub

Private Sub ZapPoley(objBlockRef As AcadBlockReference)
   'при добавлении первого блока в коллекцию блоков, записываем данные
   Dim varAtr As Variant
   
   strBlName = objBlockRef.Name
   For Each varAtr In objBlockRef.GetAttributes
      Select Case varAtr.Layer
         Case "Att~Massa"
            intMassa = Val(varAtr.TextString)
         Case "Att~Naimen"
            strNaimen = varAtr.TextString
      End Select
   Next
   
End Sub

Attribute VB_Name = "clShifrBl"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
   Dim strShifrRef As String
   'коллекция блоков изделий в шифре
   Public colBlocksConstr As New Collection

'ссылка изделия на его шифр
Public Property Get ShifrRef() As String
   ShifrRef = strShifrRef
End Property
Public Property Let ShifrRef(ByVal vNewValue As String)
   strShifrRef = vNewValue
End Property

Public Sub AddBlock(objBl As AcadBlockReference)
   'добавление блока в коллецию блоков этого шифра
   
   Dim objBlConstr As clConstr
   
   On Error Resume Next
   Set objBlConstr = colBlocksConstr.Item(objBl.Name)
   On Error GoTo 0
   If objBlConstr Is Nothing Then
      'добавляем новый блок
      Set objBlConstr = New clConstr
      objBlConstr.AddBlock objBl
      colBlocksConstr.Add objBlConstr, objBl.Name
   Else
      objBlConstr.AddBlock objBl
   End If
End Sub
