Attribute VB_Name = "FormSelectPos"
Attribute VB_Base = "0{F5C9AEB5-F462-4D63-8F91-41F270D20CC9}{28E00979-C28F-4CE0-B9A7-68E98482536D}"
Attribute VB_GlobalNameSpace = False
Attribute VB_Creatable = False
Attribute VB_PredeclaredId = True
Attribute VB_Exposed = False
Attribute VB_TemplateDerived = False
Attribute VB_Customizable = False
Option Explicit

Private Sub ComboBoxPos_Change()
   
   Dim ster As clSterjen
   Set ster = colSelectPos(ComboBoxPos.Text)
   
   ListBoxBlRef.Clear
   
   Dim br As AcadBlockReference
   For Each br In ster.colBlRef
      ListBoxBlRef.AddItem br.ObjectID
   Next
   
End Sub

Private Sub CommandButton1_Click()
   
   On Error GoTo HasError
   
   Dim ster As clSterjen
   Set ster = colSelectPos(ComboBoxPos.Text)
   
   Dim pt1 As Variant
   Dim pt2 As Variant
   
   Dim br As AcadBlockReference
   For Each br In ster.colBlRef
      If br.ObjectID = Val(ListBoxBlRef.Text) Then
         br.GetBoundingBox pt1, pt2
         ZoomWindow pt1, pt2
         Exit For
      End If
   Next
   
   Exit Sub
   
HasError:
  
End Sub

Private Sub UserForm_Activate()
   
   'обновление коллекции блоков и их позиций
   SelectArmSterBlRefs
   
   ComboBoxPos.Clear
   ListBoxBlRef.Clear
   Dim ster As clSterjen
   For Each ster In colSelectPos
      ComboBoxPos.AddItem ster.Pos
   Next
   
End Sub

Private Sub UserForm_Click()

End Sub

Attribute VB_Name = "Functions"
Option Explicit



Public Function SelectAndFilterBlRefArmElem()
   'выбор блоков с атрибутами на чертеже
   Dim selset As AcadSelectionSet
   Set selset = GetSelSet("ArmSpec")
   
   Dim intCode(1) As Integer
   Dim varDate(1) As Variant
   intCode(0) = 0: varDate(0) = "insert"
   intCode(1) = 66: varDate(1) = 1
  
   selset.SelectOnScreen intCode, varDate
   
   If selset.Count = 0 Then
      MsgBox "Блоки с атрибутами не выбраны!"
      End
   End If
   
   'фильтр блоков арм.элементов
   Set colArmElem = New Collection
   Set colBlRefNotArmElem = New Collection
   
   Dim ent As AcadEntity
   Dim vobj As Variant
   Dim blRef As AcadBlockReference
   Dim ar As AcadAttributeReference
   Dim sterjen As clSterjen
   Dim sterjen2 As clSterjen
   Dim countArmBlocks As Integer
   Dim countArmSterTypes As Integer
   
   For Each ent In selset
      Set blRef = ent
      Set sterjen = New clSterjen
      sterjen.Count = 1
      For Each vobj In blRef.GetAttributes
         Set ar = vobj
         If UCase(ar.TagString) = "НАИМЕНОВАНИЕ" Then
            sterjen.Name = ar.TextString
         End If
         If UCase(ar.TagString) = "КОЛ" Then
            sterjen.Count = Val(ar.TextString)
         End If
      Next
      If sterjen.Name <> "" Then
         countArmBlocks = countArmBlocks + 1
         Set sterjen2 = Nothing
         On Error Resume Next
         Set sterjen2 = colArmElem(sterjen.Name)
         On Error GoTo 0
         If sterjen2 Is Nothing Then
            sterjen.ObrabName
            sterjen.colBlRef.Add blRef
            colArmElem.Add sterjen, sterjen.Name
            countArmSterTypes = countArmSterTypes + 1
         Else
            sterjen2.Count = sterjen2.Count + sterjen.Count
            sterjen2.colBlRef.Add blRef
         End If
      Else
         colBlRefNotArmElem.Add blRef
      End If
   Next
   
   If colArmElem.Count = 0 Then
      MsgBox "Блоки элементов спецификаций не найдены!"
      End
   Else
      MsgBox "Кол блоков арм элементов = " & countArmBlocks & vbCr _
            & "Кол типов арм стержней = " & countArmSterTypes
   End If
   
End Function

Public Function ClearSelSets()
  'удаление всех наборов из чертежа
  'CURRENT ???!!!
  'PickFirstSelection ???!!!
  'все равно они же создадутся автоматом потом
  
  Dim selset As AcadSelectionSet
  Dim i As Integer
  
  For i = 0 To ThisDrawing.SelectionSets.Count - 1
    Set selset = ThisDrawing.SelectionSets.Item(0)
    selset.Delete
  Next
  
End Function

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function CreateSpec()
   
   Dim table As AcadTable
   Dim pt(2) As Double
   Dim numRows As Integer
   Dim curRow  As Integer
   
   numRows = colArmElem.Count + 5
   
   Set table = ThisDrawing.ActiveLayout.Block.AddTable(pt, numRows, 6, 8, 60)
   
   table.SetText 1, 0, "Поз."
   table.SetText 1, 1, "Обозначение"
   table.SetText 1, 2, "Наименование"
   table.SetText 1, 3, "Кол-во"
   table.SetText 1, 4, "Масса ед., кг"
   table.SetText 1, 5, "Примечание"
   
   table.SetColumnWidth 0, 15
   table.SetColumnWidth 1, 60
   table.SetColumnWidth 2, 65
   table.SetColumnWidth 3, 10
   table.SetColumnWidth 4, 15
   table.SetColumnWidth 5, 20
   
   Dim ster As clSterjen
   curRow = 2
   For Each ster In colArmElem
      table.SetText curRow, 0, ster.Pos
      table.SetCellAlignment curRow, 0, acMiddleCenter
      table.SetText curRow, 2, ster.Name
      table.SetCellAlignment curRow, 2, acMiddleLeft
      table.SetText curRow, 3, ster.Count
      table.SetCellAlignment curRow, 3, acMiddleCenter
      table.SetText curRow, 4, Strings.FormatNumber(ster.Weight, 2)
      table.SetCellAlignment curRow, 4, acMiddleCenter
      curRow = curRow + 1
   Next
   
   table.DeleteRows 0, 1
   
   Dim insertPt As Variant
   On Error Resume Next
   insertPt = ThisDrawing.Utility.GetPoint(, "Точка вставки спецификации")
   If Err Then
      table.Delete
      Err.Clear
   Else
      table.InsertionPoint = insertPt
   End If
   
End Function

Public Function SortArmSter()
   
   Dim i As Integer
   Dim j As Integer
   Dim intCount As Integer
   Dim ster As clSterjen
   Dim icompareClass As Integer
   
   intCount = colArmElem.Count
   
   For i = 1 To intCount - 1
      For j = 1 To intCount - i
         icompareClass = CompareArmClass(colArmElem.Item(j).ArmClass, colArmElem.Item(j + 1).ArmClass)
         If icompareClass = -1 Then
            Set ster = colArmElem.Item(j)
            colArmElem.Remove j
            colArmElem.Add ster, , , j
         ElseIf icompareClass = 0 Then
            'сравниваем диаметр стержней
            If colArmElem.Item(j).diametr < colArmElem.Item(j + 1).diametr Then
              Set ster = colArmElem.Item(j)
              colArmElem.Remove j
              colArmElem.Add ster, ster.Name, , j
            ElseIf colArmElem.Item(j).diametr = colArmElem.Item(j + 1).diametr Then
               'сравниваем длину стержней
               If colArmElem.Item(j).Lenght < colArmElem.Item(j + 1).Lenght Then
                  Set ster = colArmElem.Item(j)
                  colArmElem.Remove j
                  colArmElem.Add ster, ster.Name, , j
               End If
            End If
         End If
      Next
   Next
   
   Dim iPos As Integer
   
   For Each ster In colArmElem
      iPos = iPos + 1
      ster.Pos = iPos
   Next
   
End Function

Private Function CompareArmClass(class1 As String, class2 As String) As Integer
      
End Function

Public Function PosRecording()
   
   Dim ster As clSterjen
   Dim blRef As AcadBlockReference
   Dim ar As AcadAttributeReference
   Dim var As Variant
   
   For Each ster In colArmElem
      For Each blRef In ster.colBlRef
         For Each var In blRef.GetAttributes
            Set ar = var
            If UCase(ar.TagString) = "ПОЗ" Then
               ar.TextString = ster.Pos
               Exit For
            End If
         Next
      Next
   Next
   
End Function

Attribute VB_Name = "Main"
Option Explicit

Public colArmElem As Collection 'кол.арм.стержней
Public colBlRefNotArmElem As Collection

'для SelectPos
Public colSelectPos As Collection

Public Sub Main()
   
   'выбор блоков арм.элементов
   Functions.SelectAndFilterBlRefArmElem
   If colBlRefNotArmElem.Count > 0 Then
      MsgBox "Блоков не арм.элементо = " & colBlRefNotArmElem.Count
   End If
   
   'сортировка стержней
   SortArmSter
   
   'заполнение спецификации
   CreateSpec
   
   'заполнение атрибутов позиций в блоках
   PosRecording
   
End Sub

Public Sub SelectPos()

   FormSelectPos.Show vbModeless

End Sub

Attribute VB_Name = "SelectPos"
Option Explicit

Public Function SelectArmSterBlRefs()
      
   Dim selset As AcadSelectionSet
   Set selset = GetSelSet("SelectPos")
   
   Dim intCode(1) As Integer
   Dim varDate(1) As Variant
   intCode(0) = 0: varDate(0) = "insert"
   intCode(1) = 66: varDate(1) = 1
  
   selset.Select acSelectionSetAll, , , intCode, varDate
   
   'фильтр блоков арм.элементов
   Set colSelectPos = New Collection
   
   Dim ent As AcadEntity
   Dim vobj As Variant
   Dim blRef As AcadBlockReference
   Dim ar As AcadAttributeReference
   Dim sterjen As clSterjen
   Dim sterjen2 As clSterjen
   Dim sterjen3 As clSterjen
   
   For Each ent In selset
      Set blRef = ent
      Set sterjen = New clSterjen
      sterjen.Count = 1
      For Each vobj In blRef.GetAttributes
         Set ar = vobj
         If UCase(ar.TagString) = "НАИМЕНОВАНИЕ" Then
            sterjen.Name = ar.TextString
         End If
         If UCase(ar.TagString) = "ПОЗ" Then
            sterjen.Pos = ar.TextString
         End If
      Next
      If sterjen.Name <> "" And sterjen.Pos <> "" Then
         Set sterjen2 = Nothing
         On Error Resume Next
         Set sterjen2 = colSelectPos(sterjen.Pos)
         On Error GoTo 0
         If sterjen2 Is Nothing Then
            sterjen.colBlRef.Add blRef
            Dim i As Integer
            Dim bAdded As Boolean
            bAdded = False
            For i = 1 To colSelectPos.Count
               Set sterjen3 = colSelectPos(i)
               If Val(sterjen.Pos) < Val(sterjen3.Pos) Then
                  colSelectPos.Add sterjen, sterjen.Pos, i
                  bAdded = True
                  Exit For
               End If
            Next
            If colSelectPos.Count = 0 Then
               colSelectPos.Add sterjen, sterjen.Pos
               bAdded = True
            End If
            If bAdded = False Then
               colSelectPos.Add sterjen, sterjen.Pos, colSelectPos.Count
            End If
         Else
            'sterjen2.Count = sterjen2.Count + sterjen.Count
            sterjen2.colBlRef.Add blRef
         End If
      Else
         
      End If
   Next
      
End Function

Attribute VB_Name = "clSterjen"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public Name As String 'наименование
Public colBlRef As Collection
Public Pos As String
Public Count As Integer 'кол.стержней
Public Weight As Double 'масса 1 стержня
Public diametr As Integer 'диаметр стержня
Public Lenght As Integer 'длина стержня
Public ArmClass As String 'класс арматуры

Public Function ObrabName()
   'обработка наименования стержня.
   'определение диаметра, касса арм, длины стержня
   'пример строки наименования:
   '10-A-III, L=1100
   '10-A-I, L=500
   '10A400, L=580
   '6 Вр-1, L=800
   
   diametr = Val(Name)
   
   Dim i As Variant
   Dim i2 As Variant
   Dim s As String
   
   i = InStr(1, Name, "-", vbTextCompare)
   i2 = InStr(i, Name, ",", vbTextCompare)
   If i > 0 And i2 > 0 Then
      ArmClass = Mid(Name, i + 1, i2 - i + 1)
   End If
   
   i = InStr(i2, Name, "=", vbTextCompare)
   If i > 0 Then
      s = Mid(Name, i + 1)
      Lenght = Val(s)
   End If
   
   Weight = WeightOneMetr(diametr) * Lenght / 1000
   
End Function

Private Sub Class_Initialize()
   
   Name = ""
   Pos = ""
   ArmClass = ""
   Set colBlRef = New Collection
   
End Sub

Public Function WeightOneMetr(diametr As Integer) As Double
   
   Select Case diametr
      Case 6
         WeightOneMetr = 0.222
      Case 8
         WeightOneMetr = 0.395
      Case 10
         WeightOneMetr = 0.617
      Case 12
         WeightOneMetr = 0.888
      Case 14
         WeightOneMetr = 1.21
      Case 16
         WeightOneMetr = 1.58
      Case 18
         WeightOneMetr = 2
      Case 20
         WeightOneMetr = 2.47
      Case 22
         WeightOneMetr = 2.98
      Case 25
         WeightOneMetr = 3.85
      Case 28
         WeightOneMetr = 4.83
      Case 32
         WeightOneMetr = 6.31
      Case 36
         WeightOneMetr = 7.99
      Case 40
         WeightOneMetr = 9.87
   End Select
   
End Function
